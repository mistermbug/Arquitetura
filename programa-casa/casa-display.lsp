;;; CASA BH 0.4 - geometry-independent CAD presentation.
(defun cg:circle (p radius layer id)
 (cg:mk (list '(0 . "CIRCLE") (cons 8 layer) (cons 10 (append p '(0.0))) (cons 40 radius)) id))
(defun cd:legacy-furniture (item / b k id x0 x1 y0 y1 w d cx cy p)
 (setq b (cg:get "bounds" item) k (cg:get "kind" item) id (cg:get "id" item)
  x0 (nth 0 b) y0 (nth 1 b) x1 (nth 2 b) y1 (nth 3 b) w (- x1 x0) d (- y1 y0)
  cx (/ (+ x0 x1) 2.0) cy (/ (+ y0 y1) 2.0))
 (cg:rect b "CASA_MOVEIS" id)
 (cond
  ((member k '("bed" "single_bed" "double_bed" "bed_double" "bed_single"))
   (cg:rect (list (+ x0 80) (- y1 480) (- x1 80) (- y1 80)) "CASA_MOVEIS" id)
   (cg:line (list x0 (- y1 600)) (list x1 (- y1 600)) "CASA_MOVEIS" id))
  ((member k '("sofa" "armchair" "loveseat"))
   (cg:rect (list (+ x0 100) (+ y0 100) (- x1 100) (- y1 180)) "CASA_MOVEIS" id)
   (if (> w 1500) (cg:line (list cx (+ y0 100)) (list cx (- y1 180)) "CASA_MOVEIS" id)))
  ((member k '("chair" "desk_chair" "dining_chair" "office_chair"))
   (cg:line (list (+ x0 50) (- y1 100)) (list (- x1 50) (- y1 100)) "CASA_MOVEIS" id))
  ((member k '("sink" "basin" "tank" "laundry_sink"))
   (cg:rect (list (+ x0 100) (+ y0 100) (- x1 100) (- y1 100)) "CASA_MOVEIS" id)
   (cg:circle (list cx cy) 35 "CASA_MOVEIS" id))
  ((= k "toilet") (cg:circle (list cx (+ y0 (* d 0.4))) (* w 0.28) "CASA_MOVEIS" id)
   (cg:rect (list (+ x0 60) (- y1 200) (- x1 60) y1) "CASA_MOVEIS" id))
  ((member k '("stove" "cooktop"))
   (foreach p (list (list (+ x0 (* w 0.28)) (+ y0 (* d 0.28))) (list (+ x0 (* w 0.72)) (+ y0 (* d 0.28)))
    (list (+ x0 (* w 0.28)) (+ y0 (* d 0.72))) (list (+ x0 (* w 0.72)) (+ y0 (* d 0.72))))
    (cg:circle p (* (min w d) 0.12) "CASA_MOVEIS" id)))
  ((= k "washer") (cg:circle (list cx cy) (* (min w d) 0.40) "CASA_MOVEIS" id))
  ((= k "shower") (cg:line (list x0 y0) (list x1 y1) "CASA_MOVEIS" id)
   (cg:circle (list cx cy) 40 "CASA_MOVEIS" id))
  ((member k '("wardrobe" "rack" "tv_console" "tv_rack"))
   (cg:line (list cx y0) (list cx y1) "CASA_MOVEIS" id))
  ((= k "car")
   (cg:rect (list (+ x0 180) (+ y0 (* d 0.22)) (- x1 180) (- y1 (* d 0.22))) "CASA_MOVEIS" id)
   (cg:line (list (+ x0 180) (+ y0 (* d 0.45))) (list (- x1 180) (+ y0 (* d 0.45))) "CASA_MOVEIS" id)
   (cg:line (list (+ x0 180) (- y1 (* d 0.40))) (list (- x1 180) (- y1 (* d 0.40))) "CASA_MOVEIS" id))))

(defun cg:draw-furniture (item / points)
 (if (cg:get "symbol_lines" item)
  (progn
   (cg:rect (cg:get "bounds" item) "CASA_MOVEIS" (cg:get "id" item))
   (foreach points (cg:get "symbol_lines" item) (cd:polyline points nil "CASA_MOVEIS" (cg:get "id" item))))
  (cd:legacy-furniture item)))

(defun cg:draw-opening (o walls / wall c width thick horiz a b id style room box sign tip ang0 ang1)
 (setq wall (cg:find-id (cg:get "wall_id" o) walls) c (cg:get "center" o)
  width (cg:get "width" o) thick (cg:get "thickness" wall) id (cg:get "id" o)
  horiz (equal (cadr (cg:get "start" wall)) (cadr (cg:get "end" wall)) 0.01)
  style (cg:opt "door_style" o "swing"))
 (if horiz
  (setq a (list (- (car c) (/ width 2)) (cadr c)) b (list (+ (car c) (/ width 2)) (cadr c)))
  (setq a (list (car c) (- (cadr c) (/ width 2))) b (list (car c) (+ (cadr c) (/ width 2)))))
 (cond
  ((= (cg:get "kind" o) "window")
   (cg:line a b "CASA_JANELAS" id)
   (if horiz
    (progn (cg:line (list (car a) (+ (cadr a) (/ thick 2))) (list (car b) (+ (cadr b) (/ thick 2))) "CASA_JANELAS" id)
     (cg:line (list (car a) (- (cadr a) (/ thick 2))) (list (car b) (- (cadr b) (/ thick 2))) "CASA_JANELAS" id))
    (progn (cg:line (list (+ (car a) (/ thick 2)) (cadr a)) (list (+ (car b) (/ thick 2)) (cadr b)) "CASA_JANELAS" id)
     (cg:line (list (- (car a) (/ thick 2)) (cadr a)) (list (- (car b) (/ thick 2)) (cadr b)) "CASA_JANELAS" id))))
  ((= style "passage") nil)
  ((= style "sliding") (cg:line a b "CASA_PORTAS" id))
  (T
   (setq room (cg:find-id (cg:get "room_id" o) (cg:get "rooms" *cg-drawing-model*)) box (cg:get "bounds" room))
   (if horiz
    (progn
     (setq sign (if (and box (< (/ (+ (nth 1 box) (nth 3 box)) 2) (cadr c))) -1 1)
      tip (list (car a) (+ (cadr a) (* sign width))))
     (if (= sign 1) (setq ang0 0.0 ang1 (/ pi 2)) (setq ang0 (* 1.5 pi) ang1 (* 2 pi))))
    (progn
     (setq sign (if (and box (< (/ (+ (nth 0 box) (nth 2 box)) 2) (car c))) -1 1)
      tip (list (+ (car a) (* sign width)) (cadr a)))
     (if (= sign 1) (setq ang0 0.0 ang1 (/ pi 2)) (setq ang0 (/ pi 2) ang1 pi))))
   (cg:line a tip "CASA_PORTAS" id)
   (cg:mk (list '(0 . "ARC") '(8 . "CASA_PORTAS") (cons 10 (append a '(0.0)))
    (cons 40 width) (cons 50 ang0) (cons 51 ang1)) id))))

(defun cg:label-box (item / b id txt w h tw th px py cand best score bestscore f fb dims)
 (setq b (cg:get "bounds" item) id (cg:get "id" item) txt (cg:opt "name" item (cg:get "kind" item))
  w (- (nth 2 b) (car b)) h (- (nth 3 b) (cadr b)) tw (min (- w 100) (max 1150 (* 82 (strlen txt)))) th 620 best nil bestscore 1e20)
 (foreach cand '((0.5 0.5) (0.5 0.4) (0.5 0.7) (0.25 0.45) (0.75 0.45) (0.5 0.15) (0.5 0.85))
  (setq px (+ (car b) (* (- w tw) (car cand))) py (+ (cadr b) (* (- h th) (cadr cand)))
   fb (list px py (+ px tw) (+ py th)) score 0)
  (foreach f (cg:get "furniture" *cg-drawing-model*)
   (if (cf:hit fb (cg:get "bounds" f)) (setq score (+ score 1))))
  (foreach f (cf:doors b *cg-drawing-model*) (if (cf:hit fb f) (setq score (+ score 1))))
  (if (< score bestscore) (setq best (list px py) bestscore score)))
 (setq *cj-label-boxes* (cons (list (car best) (cadr best) (+ (car best) tw) (+ (cadr best) th)) *cj-label-boxes*))
 (cg:text (list (car best) (+ (cadr best) 430)) txt 140 "CASA_TEXTOS" id)
 (cg:text (list (car best) (+ (cadr best) 220)) (strcat (rtos (/ (* w h) 1e6) 2 2) " m2") 120 "CASA_TEXTOS" id)
 (cg:text best (strcat (rtos (/ w 1000.0) 2 2) " x " (rtos (/ h 1000.0) 2 2) " m") 110 "CASA_TEXTOS" id))

(defun cg:draw-model (model / site house walls rooms zones item b id x0 y0 x1 y1 tx yy area cutY a z ht wt xs v c width sill nx ny angle endp widthpairs pair dimy sidepos host)
 (setq *cj-label-boxes* nil *cg-drawing-model* model site (cg:get "site_bounds" model) house (cg:get "house_bounds" model)
  walls (cg:get "walls" model) rooms (cg:get "rooms" model) zones (cg:get "zones" model)
  x0 (nth 0 house) y0 (nth 1 house) x1 (nth 2 house) y1 (nth 3 house))
 (foreach item '(("CASA_LOTE" 8) ("CASA_PAREDES" 7) ("CASA_PORTAS" 2) ("CASA_JANELAS" 4)
  ("CASA_MOVEIS" 3) ("CASA_TEXTOS" 7) ("CASA_COTAS" 6) ("CASA_ESTUDO" 8) ("CASA_EXTERNO" 3) ("CASA_COBERTURA" 2) ("CASA_ACESSO" 4))
  (cg:layer (car item) (cadr item)))
 (cg:rect site "CASA_LOTE" "SITE")
 (foreach item (cg:get "outdoor" model) (cg:rect (cg:get "bounds" item) "CASA_EXTERNO" (cg:get "id" item)) (cg:label-box item))
 (if (cg:get "entry_path" model)
  (progn
   (cd:polyline (cg:get "points" (cg:get "entry_path" model)) nil "CASA_ACESSO" "ENTRY-PATH")
   (setq a (car (cg:get "points" (cg:get "entry_path" model))))
   (cg:text (list (+ (car a) 200) (+ (cadr a) 250))
    (strcat "Acesso " (rtos (/ (cg:get "length" (cg:get "entry_path" model)) 1000.0) 2 2) " m") 120 "CASA_TEXTOS" "ENTRY-PATH")))
 (cj:draw model)
 (foreach item (cg:get "openings" model) (cg:draw-opening item walls))
 (foreach item (cg:get "furniture" model) (cg:draw-furniture item))
 (foreach item rooms
  (if (not (member (cg:get "kind" item) '("social" "corridor"))) (cg:label-box item)))
 (foreach item zones
  (setq host (cg:find-id (cg:get "room_id" item) rooms))
  (if (and host (= (cg:get "kind" host) "social")) (cg:label-box item)))
 (cj:dimensions model)
 (setq tx (+ (nth 2 site) 3300) yy (nth 3 site) area 0)
 (cg:text (list tx yy) "CASA BH 0.4 | ESTUDO PRELIMINAR" 280 "CASA_TEXTOS" "TITLE")
 (setq yy (- yy 480))
 (cg:text (list tx yy) (strcat (cg:opt "layout_name" model "Alternativa") " | " (cg:opt "integration_name" model "")) 190 "CASA_TEXTOS" "TITLE")
 (setq yy (- yy 380))
 (cg:text (list tx yy) (strcat "Semente " (itoa (fix (cg:get "seed" model))) " | " (cg:get "project_id" model)) 160 "CASA_TEXTOS" "TITLE")
 (foreach item rooms
  (setq yy (- yy 330) area (+ area (cg:get "net_area_m2" item)))
  (cg:text (list tx yy) (strcat (cg:get "name" item) ": " (rtos (cg:get "net_area_m2" item) 2 2) " m2") 170 "CASA_TEXTOS" "SCHEDULE"))
 (setq yy (- yy 450))
 (cg:text (list tx yy) (strcat "Util " (rtos area 2 2) " m2 | Casa " (rtos (cg:get "gross_area_m2" model) 2 2) " m2") 175 "CASA_TEXTOS" "SCHEDULE")
 (setq yy (- yy 350))
 (cg:text (list tx yy) (strcat "Circulacao: " (rtos (cg:opt "circulation_area_m2" model 0) 2 2) " m2 ("
  (rtos (* 100 (cg:opt "circulation_fraction" model 0)) 2 1) "% da area util)") 160 "CASA_TEXTOS" "METRICS")
 (setq yy (- yy 300))
 (cg:text (list tx yy) (strcat "Janelas: " (itoa (fix (cg:opt "windows_count" model 0))) " | Area geometrica: "
  (rtos (cg:opt "window_area_m2" model 0) 2 2) " m2") 160 "CASA_TEXTOS" "METRICS")
 (foreach item (cg:get "validations" model)
  (setq yy (- yy 300))
  (cg:text (list tx yy) (strcat (cg:get "rule_id" item) ": " (cg:get "status" item)) 150 "CASA_TEXTOS" "CHECK"))
 (foreach item '("Estudo hipotetico. Faixas livres nao sao recuos legais de BH."
   "Cotas em metros. Garagem descoberta. Cobertura conceitual em laje."
   "Conforto: indicadores geometricos; desempenho nao simulado."
   "Revit recebe geracao; edicoes manuais CAD nao sincronizadas.")
  (setq yy (- yy 300)) (cg:text (list tx yy) item 150 "CASA_TEXTOS" "NOTES"))
 ;; North convention: clockwise from +Y, independent of CAD UCS.
 (setq nx (+ (nth 2 site) 1500) ny (- (nth 3 site) 2300)
  angle (* (/ pi 180.0) (cg:opt "north_degrees" model (cg:opt "north" model 0.0)))
  endp (list (+ nx (* 1500 (sin angle))) (+ ny (* 1500 (cos angle)))))
 (cg:line (list nx ny) endp "CASA_ESTUDO" "NORTH")
 (cg:circle endp 90 "CASA_ESTUDO" "NORTH")
 (cg:text (list (+ (car endp) 120) (+ (cadr endp) 120)) "N*" 220 "CASA_TEXTOS" "NORTH")
 (cg:text (list tx (- yy 380)) "* Norte informado; confirmar no levantamento." 150 "CASA_TEXTOS" "NORTH")
 (cd:sections model tx yy)
 (princ))

(defun c:CASA_ALTERNATIVAS (/ origin params model index seed pid ok step)
 (if (and (cg:ensure-core) (cg:form))
  (progn (setq origin (getpoint "\nPonto inicial para comparar tres organizacoes: "))
   (if origin
    (progn (setq origin (trans origin 1 0) index 1 ok 0 seed (fix (cg:get "seed" *casa-params*))
      step (+ (cg:get "lot_width" *casa-params*) 28000))
     (repeat 3
      (setq pid (strcat "CG3-" (itoa (getvar "MILLISECS")) "-" (itoa index))
       params (append (list (cons "layout" index) (cons "seed" seed)
        (cons "origin_x" (+ (car origin) (* (1- index) step))) (cons "origin_y" (cadr origin)) (cons "project_id" pid)) *casa-params*)
       model (cg:generate params))
      (if (cg:get "error" model) (princ (strcat "\nAlternativa " (itoa index) ": " (cg:get "error" model)))
       (if (cg:commit model) (setq ok (1+ ok))))
      (setq index (1+ index)))
     (princ (strcat "\n" (itoa ok) " alternativas desenhadas. CASA_EXPORTAR: selecione a alternativa desejada."))))))
 (princ))
(defun c:CASA_AJUDA ()
 (alert "CASA_GERAR: uma alternativa. CASA_ALTERNATIVAS: compara tres organizacoes.\nCASA_EXPORTAR: snapshot JSON para Revit.\nUse Modelo, INSUNITS=4. Leia LEIA-ME.md.\nRegras municipais e desempenho ambiental ainda pendentes.") (princ))
(princ "\nCASA BH 0.4: CASA_GERAR, CASA_ALTERNATIVAS, CASA_EXPORTAR.") (princ)
