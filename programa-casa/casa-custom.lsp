(defun ce:raise (message) (princ (strcat "\n" message)) (exit))
;;; CASA BH: persisted furniture dimensions. No executable data in JSON parser.
(defun ce:put (k v obj) (if (assoc k obj) (subst (cons k v) (assoc k obj) obj) (append obj (list (cons k v)))))
(defun cj:space () (while (and (<= cj:i cj:n) (member (ascii (substr cj:s cj:i 1)) '(9 10 13 32))) (setq cj:i (1+ cj:i))))
(defun cj:expect (s) (cj:space) (if (/= (substr cj:s cj:i 1) s) (ce:raise "JSON invalido.")) (setq cj:i (1+ cj:i)))
(defun cj:string (/ out c hex n j code)
 (cj:expect "\"") (setq out "" c "")
 (while (and (<= cj:i cj:n) (/= (setq c (substr cj:s cj:i 1)) "\""))
  (setq cj:i (1+ cj:i))
  (if (= c "\\")
   (progn (setq c (substr cj:s cj:i 1) cj:i (1+ cj:i))
    (cond ((= c "n") (setq c (chr 10))) ((= c "r") (setq c (chr 13))) ((= c "t") (setq c (chr 9)))
     ((= c "b") (setq c (chr 8))) ((= c "f") (setq c (chr 12)))
     ((= c "u") (setq hex (strcase (substr cj:s cj:i 4)) n 0 j 1)
      (repeat 4 (setq code (vl-string-search (substr hex j 1) "0123456789ABCDEF"))
       (if (null code) (ce:raise "Escape JSON invalido.")) (setq n (+ (* n 16) code) j (1+ j)))
      (setq c (chr n) cj:i (+ cj:i 4)))
     ((not (member c '("\"" "\\" "/"))) (ce:raise "Escape JSON invalido.")))))
  (setq out (strcat out c)))
 (cj:expect "\"") out)
(defun cj:value (/ c out key start token val)
 (cj:space) (setq c (substr cj:s cj:i 1))
 (cond ((= c "\"") (cj:string))
  ((member c '("[" "{"))
   (setq cj:i (1+ cj:i) out nil) (cj:space)
   (if (/= (substr cj:s cj:i 1) (if (= c "[") "]" "}"))
    (progn
     (if (= c "{") (progn (setq key (cj:string)) (cj:expect ":") (setq val (cons key (cj:value)))) (setq val (cj:value)))
     (setq out (list val)) (cj:space)
     (while (= (substr cj:s cj:i 1) ",")
      (setq cj:i (1+ cj:i))
      (if (= c "{") (progn (setq key (cj:string)) (cj:expect ":") (setq val (cons key (cj:value)))) (setq val (cj:value)))
      (setq out (cons val out)) (cj:space))))
   (cj:expect (if (= c "[") "]" "}")) (reverse out))
  (T (setq start cj:i)
   (while (and (<= cj:i cj:n) (not (member (substr cj:s cj:i 1) '(" " "\t" "\r" "\n" "," "]" "}")))) (setq cj:i (1+ cj:i)))
   (setq token (substr cj:s start (- cj:i start)))
   (cond ((= token "true") 'cj:true) ((= token "false") 'cj:false) ((= token "null") 'cj:null)
    ((and (> (strlen token) 0) (not (wcmatch token "*[~0-9.eE+-]*")) (setq val (distof token 2))) val)
    (T (ce:raise "Numero JSON invalido."))))))
(defun cj:parse (text / cj:s cj:i cj:n val)
 (setq cj:s text cj:i 1 cj:n (strlen text) val (cj:value)) (cj:space)
 (if (<= cj:i cj:n) (ce:raise "Conteudo apos JSON.")) val)
(defun ce:identity (entity / xd)
 (setq xd (cdr (cadr (assoc -3 (entget entity '("CASA_BH"))))))
 (if (and xd (= (caar xd) 1000) (= (car (cadr xd)) 1000)) (list (cdar xd) (cdr (cadr xd)))))
(defun ce:entities (pid id / ss i out en)
 (setq ss (ssget "_X" '((-3 ("CASA_BH")))) i 0 out nil)
 (if ss (repeat (sslength ss) (setq en (ssname ss i) i (1+ i))
  (if (equal (ce:identity en) (list pid id)) (setq out (cons en out))))) out)
(defun ce:save (model / dict rec data str chunks i fresh pid)
 (setq dict (cdr (assoc -1 (dictsearch (namedobjdict) "CASA_BH_MODELS")))
  rec (dictsearch dict (cg:get "project_id" model)))
 (if (not rec) (ce:raise "Snapshot do projeto ausente."))
 (setq data (vl-remove-if '(lambda (p) (= (car p) 1)) (entget (cdr (assoc -1 rec)))) str (cg:json model) chunks nil i 1)
 (while (<= i (strlen str)) (setq chunks (cons (cons 1 (substr str i 240)) chunks) i (+ i 240)))
 ;; XRECORD entmod appends payload in AutoCAD 2027. Replace the owned record
 ;; inside the same UNDO group, rather than concatenating two JSON documents.
 (setq pid (cg:get "project_id" model)
  fresh (entmakex (append '((0 . "XRECORD") (100 . "AcDbXrecord") (280 . 1)) (reverse chunks))))
 (if (not fresh) (ce:raise "Falha ao criar snapshot."))
 (if (not (dictremove dict pid)) (ce:raise "Falha ao liberar snapshot anterior."))
 (if (not (dictadd dict pid fresh)) (ce:raise "Falha ao registrar snapshot atualizado."))
 (if (entget (cdr (assoc -1 rec))) (entdel (cdr (assoc -1 rec)))))
(defun ce:point (p old new)
 (list (+ (car new) (* (- (car p) (car old)) (/ (- (nth 2 new) (car new)) (- (nth 2 old) (car old)))))
       (+ (cadr new) (* (- (cadr p) (cadr old)) (/ (- (nth 3 new) (cadr new)) (- (nth 3 old) (cadr old)))))))
(defun ce:resize (item width depth height / old new use dx dy angle lines result original ln)
 (setq old (cg:get "bounds" item) angle (cg:opt "rotation" item 0) original (cg:opt "source_bounds_before_edit" item old))
 (if (member angle '(90 270)) (setq dx depth dy width) (setq dx width dy depth))
 (if (or (< dx (max 250 (* 0.65 (- (nth 2 original) (car original)))) )
         (< dy (max 250 (* 0.65 (- (nth 3 original) (cadr original)))) ) (< height 100) (> height 3000))
  (ce:raise "Medidas fora da faixa do modelo: minimo 65% da base/250 mm; altura 100 a 3000 mm."))
 (setq new (list (- (/ (+ (car old) (nth 2 old)) 2.0) (/ dx 2.0)) (- (/ (+ (cadr old) (nth 3 old)) 2.0) (/ dy 2.0))
                 (+ (/ (+ (car old) (nth 2 old)) 2.0) (/ dx 2.0)) (+ (/ (+ (cadr old) (nth 3 old)) 2.0) (/ dy 2.0)))
  use (cg:opt "use_bounds" item old) lines nil)
 (foreach ln (cg:get "symbol_lines" item) (setq lines (cons (mapcar '(lambda (p) (ce:point p old new)) ln) lines)))
 (setq result (ce:put "bounds" new item) result (ce:put "height" height result)
  result (ce:put "use_bounds" (mapcar '+ new (mapcar '- use old)) result)
  result (ce:put "symbol_lines" (reverse lines) result)
  result (ce:put "source_bounds_before_edit" original result)
  result (ce:put "dimension_revision" (1+ (cg:opt "dimension_revision" item 0)) result)) result)
(defun ce:validate (item model / host box others reason f door)
 (setq host (cg:find-id (cg:get "room_id" item) (append (cg:get "rooms" model) (cg:get "outdoor" model)))
  box (if host (cg:get "bounds" host)) reason nil)
 (cond ((not box) (setq reason "Ambiente do movel nao identificado."))
  ((not (and (cf:inside (cg:get "bounds" item) box) (cf:inside (cg:get "use_bounds" item) box))) (setq reason "Movel ou faixa de uso invade a parede/limite do ambiente.")))
 (foreach f (cg:get "furniture" model)
  (if (/= (cg:get "id" f) (cg:get "id" item))
   (if (or (cf:hit (cg:get "bounds" item) (cg:get "bounds" f))
      (and (not (and (member (cg:get "kind" item) '("bed_double" "bed_single")) (= (cg:get "kind" f) "nightstand"))) (cf:hit (cg:get "use_bounds" item) (cg:get "bounds" f)))
      (and (not (and (member (cg:get "kind" f) '("bed_double" "bed_single")) (= (cg:get "kind" item) "nightstand"))) (cf:hit (cg:get "use_bounds" f) (cg:get "bounds" item))))
    (setq reason (strcat "Conflito com movel/faixa de uso: " (cg:get "id" f))))))
 (if box (foreach door (cf:doors box model) (if (cf:hit (cg:get "bounds" item) door) (setq reason "Conflito com abertura de porta."))))
 (if (not (cf:window-clear (list item) model)) (setq reason "Altura/posicao bloqueia janela."))
 (if (> (cg:get "height" item) (cg:get "height" (car (cg:get "walls" model)))) (setq reason "Movel acima do pe-direito.")) reason)
(defun ce:apply (model item / *error* undoStarted entities en old b poly *cg-pid* *cg-drawing-model* newmodel)
 (setq *cg-pid* (cg:get "project_id" model) *cg-drawing-model* model undoStarted nil
  entities (ce:entities *cg-pid* (cg:get "id" item)) old (cg:find-id (cg:get "id" item) (cg:get "furniture" model)) b (cg:get "bounds" old))
 (defun *error* (message)
  (if undoStarted (progn (command-s "_.UNDO" "_End") (command-s "_.U"))) (princ (strcat "\nEdicao cancelada: " message)) (princ))
 (if (not entities) (ce:raise "Geometria do movel ausente."))
 ;; Outline signature detects moved/scaled outlines before regenerating symbols.
 (setq poly nil)
 (foreach en entities
  (if (= (cdr (assoc 0 (entget en))) "LWPOLYLINE")
   (if (equal (mapcar 'cdr (vl-remove-if-not '(lambda (p) (= (car p) 10)) (entget en)))
     (list (list (car b) (cadr b)) (list (nth 2 b) (cadr b)) (list (nth 2 b) (nth 3 b)) (list (car b) (nth 3 b))) 0.1) (setq poly T)))
  (if (= 4 (logand 4 (cdr (assoc 70 (tblsearch "LAYER" (cdr (assoc 8 (entget en)))))))) (ce:raise "Camada de movel bloqueada.")))
 (if (not poly) (ce:raise "Contorno alterado manualmente. Desfaca MOVE/SCALE antes de editar parametros."))
 (setq newmodel (ce:put "furniture" (mapcar '(lambda (f) (if (= (cg:get "id" f) (cg:get "id" item)) item f)) (cg:get "furniture" model)) model))
 (command-s "_.UNDO" "_Begin") (setq undoStarted T)
 (foreach en entities (if (not (entdel en)) (ce:raise "Falha ao remover simbolo anterior.")))
 (cg:draw-furniture item) (ce:save newmodel)
 (command-s "_.UNDO" "_End") (setq undoStarted nil *casa-last* newmodel) newmodel)
(defun c:CASA_MOVEL_EDITAR (/ *error* selection ids model item b width depth height changed reason)
 (defun *error* (message) (princ (strcat "\nEdicao cancelada: " message)) (princ))
 (setq selection (entsel "\nSelecione uma linha do movel CASA: "))
 (if selection
  (progn
   (setq ids (ce:identity (car selection))) (if (not ids) (ce:raise "Selecione um movel gerado pelo CASA."))
   (setq model (cj:parse (cg:stored-json (car ids))) item (cg:find-id (cadr ids) (cg:get "furniture" model)))
   (if (not item) (ce:raise "Entidade nao e movel do projeto."))
   (setq b (cg:get "bounds" item) width (- (nth 2 b) (car b)) depth (- (nth 3 b) (cadr b)) height (cg:get "height" item))
   (if (member (cg:opt "rotation" item 0) '(90 270)) (setq width (- (nth 3 b) (cadr b)) depth (- (nth 2 b) (car b))))
   (princ (strcat "\n" (cg:get "id" item) " | " (cg:get "kind" item) " | Medidas locais em METROS. Centro e orientacao preservados."))
   (initget 6) (setq width (* 1000 (cond ((getreal (strcat "\nLargura <" (rtos (/ width 1000.0) 2 3) ">: "))) (T (/ width 1000.0)))))
   (initget 6) (setq depth (* 1000 (cond ((getreal (strcat "\nProfundidade <" (rtos (/ depth 1000.0) 2 3) ">: "))) (T (/ depth 1000.0)))))
   (initget 6) (setq height (* 1000 (cond ((getreal (strcat "\nAltura <" (rtos (/ height 1000.0) 2 3) ">: "))) (T (/ height 1000.0)))))
   (setq changed (ce:resize item width depth height) reason (ce:validate changed model))
   (if reason (ce:raise reason))
   (if (ce:apply model changed) (princ "\nMovel e snapshot atualizados. Salve o DWG e use CASA_EXPORTAR para enviar as medidas ao Revit.")))) (princ))
(princ "\nCASA_MOVEL_EDITAR: dimensoes de moveis em metros, com exportacao para Revit.") (princ)
