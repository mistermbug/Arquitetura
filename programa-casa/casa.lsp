;;; CASA BH - AutoCAD 2027 / AutoLISP. ASCII source for legacy LISPSYS.
(vl-load-com)
(setq *casa-version* "0.4.0")
(setq *casa-fields* '("lot_width" "lot_depth" "house_width" "wall_internal" "wall_external" "height" "corridor"
  "bedrooms" "bathrooms" "living" "kitchens" "laundry" "dining" "office" "front" "rear" "side" "seed" "occupants" "parking" "layout" "integration" "north"))
(if (not *casa-input*)
 (setq *casa-input* '(("lot_width" . "12") ("lot_depth" . "30") ("house_width" . "9")
  ("wall_internal" . "0.15") ("wall_external" . "0.20") ("height" . "2.8") ("corridor" . "1.2") ("bedrooms" . "3")
  ("bathrooms" . "1") ("living" . "1") ("kitchens" . "1") ("laundry" . "1")
  ("dining" . "1") ("office" . "0") ("front" . "6.5") ("rear" . "3") ("side" . "1.5")
  ("seed" . "42") ("furniture" . "1"))))
(foreach pair '(("wall_internal" . "0.15") ("wall_external" . "0.20") ("occupants" . "4") ("parking" . "1") ("layout" . "0") ("integration" . "0") ("north" . "0") ("terrace" . "1"))
 (if (not (assoc (car pair) *casa-input*)) (setq *casa-input* (cons pair *casa-input*))))
(defun cg:ensure-core (/ file)
 (if (not *casa-dir*)
  (progn
   (setq file (findfile "casa-core.lsp"))
   (if (not file) (setq file (getfiled "Selecione casa-core.lsp na pasta do programa" "" "lsp" 0)))
   (if file (setq *casa-dir* (vl-filename-directory file)))))
 (if *casa-dir* (progn (load (strcat *casa-dir* "/casa-core.lsp")) T) nil))
(defun cg:accept (/ key raw value params inputs err lengthkeys)
 (setq params nil inputs nil err nil lengthkeys '("lot_width" "lot_depth" "house_width" "wall_internal" "wall_external" "height" "corridor" "front" "rear" "side"))
 (foreach key *casa-fields*
  (setq raw (get_tile key) value (distof (vl-string-translate "," "." raw) 2))
  (setq inputs (cons (cons key raw) inputs))
  (if value
   (setq params (cons (cons key (if (member key lengthkeys) (* value 1000.0) value)) params))
   (setq err (strcat "Preencha um numero valido em: " key))))
 (setq params (cons (cons "terrace" (atoi (get_tile "terrace"))) params) inputs (cons (cons "terrace" (get_tile "terrace")) inputs))
 (setq params (cons (cons "furniture" (atoi (get_tile "furniture"))) params)
       inputs (cons (cons "furniture" (get_tile "furniture")) inputs))
 (if (not err) (setq err (cg:validate-input params)))
 (if err (set_tile "error" err)
  (progn (setq *casa-input* inputs *casa-params* params) (done_dialog 1))))
(defun cg:form (/ dlg result pair)
 (setq dlg (load_dialog (strcat *casa-dir* "/casa.dcl")))
 (if (and (> dlg 0) (new_dialog "casa_form" dlg))
  (progn
   (start_list "layout") (mapcar 'add_list '("Aleatoria" "Social na frente" "Social no fundo" "Nucleo de convivencia")) (end_list)
   (start_list "integration") (mapcar 'add_list '("Variar" "Aberta" "Semiaberta" "Fechada")) (end_list)
   (foreach pair *casa-input* (set_tile (car pair) (cdr pair)))
   (action_tile "accept" "(cg:accept)")
   (action_tile "cancel" "(done_dialog 0)")
   (setq result (start_dialog)) (unload_dialog dlg) (= result 1))
  (progn (if (> dlg 0) (unload_dialog dlg)) (alert "Nao foi possivel abrir casa.dcl.") nil)))
(defun cg:escape (str / i ch out)
 (setq i 1 out "")
 (repeat (strlen str)
  (setq ch (substr str i 1) out (strcat out
   (cond ((= ch "\"") "\\\"") ((= ch "\\") "\\\\") ((= ch (chr 10)) "\\n")
    ((= ch (chr 13)) "\\r") ((= ch (chr 9)) "\\t") (T ch))) i (1+ i))) out)
(defun cg:join (items separator / out item)
 (setq out "") (foreach item items (setq out (strcat out (if (= out "") "" separator) item))) out)
(defun cg:number-json (value / text)
 (setq text (rtos value 2 6))
 (if (= (substr text 1 1) ".") (setq text (strcat "0" text)))
 (if (= (substr text 1 2) "-.") (setq text (strcat "-0" (substr text 2)))) text)
(defun cg:json (value / pair out)
 (cond ((eq value 'cj:true) "true") ((eq value 'cj:false) "false") ((eq value 'cj:null) "null") ((null value) "[]")
  ((= (type value) 'STR) (strcat "\"" (cg:escape value) "\""))
  ((numberp value) (cg:number-json value))
  ((and (listp value) (listp (car value)) (= (type (caar value)) 'STR))
   (setq out nil)
   (foreach pair value (setq out (append out (list (strcat (cg:json (car pair)) ":" (cg:json (cdr pair)))))))
   (strcat "{" (cg:join out ",") "}"))
  ((listp value) (strcat "[" (cg:join (mapcar 'cg:json value) ",") "]"))
  (T "null")))
(defun cg:write-json (model file / stream)
 (setq stream (open file "w"))
 (if stream (progn (write-line (cg:json model) stream) (close stream) T) nil))
(defun cg:tag (entity id / data)
 (if entity
  (progn (setq data (entget entity))
   (entmod (append data (list (list -3 (list "CASA_BH" (cons 1000 *cg-pid*) (cons 1000 id)))))) entity)))
(defun cg:mk (data id / entity)
 (setq entity (entmakex data))
 (if (not entity) (progn (princ "\nFalha ao criar entidade. Operacao cancelada.") (exit)))
 (cg:tag entity id))
(defun cg:layer (name color)
 (if (not (tblsearch "LAYER" name))
  (entmake (list '(0 . "LAYER") '(100 . "AcDbSymbolTableRecord") '(100 . "AcDbLayerTableRecord")
   (cons 2 name) '(70 . 0) (cons 62 color) '(6 . "Continuous")))))
(defun cg:line (a b layer id)
 (cg:mk (list '(0 . "LINE") (cons 8 layer) (cons 10 (append a '(0.0))) (cons 11 (append b '(0.0)))) id))
(defun cg:rect (box layer id / x0 y0 x1 y1)
 (setq x0 (nth 0 box) y0 (nth 1 box) x1 (nth 2 box) y1 (nth 3 box))
 (cg:mk (list '(0 . "LWPOLYLINE") '(100 . "AcDbEntity") (cons 8 layer)
  '(100 . "AcDbPolyline") '(90 . 4) '(70 . 1)
  (cons 10 (list x0 y0)) (cons 10 (list x1 y0)) (cons 10 (list x1 y1)) (cons 10 (list x0 y1))) id))
(defun cg:text (point str size layer id)
 (cg:mk (list '(0 . "TEXT") (cons 8 layer) (cons 10 (append point '(0.0))) (cons 40 size)
  (cons 1 str) '(50 . 0.0) '(7 . "Standard")) id))
(defun cg:dim (a b point id)
 (setvar "CLAYER" "CASA_COTAS")
 (command-s "_.DIMLINEAR" "_non" (append a '(0.0)) "_non" (append b '(0.0)) "_non" (append point '(0.0)))
 (cg:tag (entlast) id))
(defun cg:wall-segment (start end lo hi thick horizontal id / x y)
 (if (> (- hi lo) 0.1)
  (if horizontal
   (cg:rect (list (+ (car start) lo) (- (cadr start) (/ thick 2.0))
    (+ (car start) hi) (+ (cadr start) (/ thick 2.0))) "CASA_PAREDES" id)
   (cg:rect (list (- (car start) (/ thick 2.0)) (+ (cadr start) lo)
    (+ (car start) (/ thick 2.0)) (+ (cadr start) hi)) "CASA_PAREDES" id))))
(defun cg:draw-wall (wall openings / a b horiz len intervals opening at current gap thick id)
 (setq a (cg:get "start" wall) b (cg:get "end" wall) horiz (equal (cadr a) (cadr b) 0.01)
  len (distance a b) thick (cg:get "thickness" wall) id (cg:get "id" wall) intervals nil current 0.0)
 (foreach opening openings
  (if (= (cg:get "wall_id" opening) id)
   (progn
    (setq at (distance a (cg:get "center" opening)))
    (setq intervals (cons (list (- at (/ (cg:get "width" opening) 2.0))
      (+ at (/ (cg:get "width" opening) 2.0))) intervals)))))
 (setq intervals (vl-sort intervals '(lambda (u v) (< (car u) (car v)))))
 (foreach gap intervals
  (cg:wall-segment a b current (car gap) thick horiz id)
  (setq current (cadr gap)))
 (cg:wall-segment a b current len thick horiz id))
(defun cg:find-id (id records / result record)
 (setq result nil) (foreach record records (if (= id (cg:get "id" record)) (setq result record))) result)
(defun cg:draw-opening (opening walls / wall c width horiz a b h id hinge tip angle0 angle1 roomside)
 (setq wall (cg:find-id (cg:get "wall_id" opening) walls) c (cg:get "center" opening)
  width (cg:get "width" opening) h (/ (cg:get "thickness" wall) 2.0)
  horiz (equal (cadr (cg:get "start" wall)) (cadr (cg:get "end" wall)) 0.01)
  id (cg:get "id" opening))
 (if horiz
  (setq a (list (- (car c) (/ width 2.0)) (cadr c)) b (list (+ (car c) (/ width 2.0)) (cadr c)))
  (setq a (list (car c) (- (cadr c) (/ width 2.0))) b (list (car c) (+ (cadr c) (/ width 2.0)))))
 (if (= (cg:get "kind" opening) "window")
  (progn
   (cg:line a b "CASA_JANELAS" id)
   (if horiz
    (progn (cg:line (list (car a) (- (cadr a) h)) (list (car b) (- (cadr b) h)) "CASA_JANELAS" id)
     (cg:line (list (car a) (+ (cadr a) h)) (list (car b) (+ (cadr b) h)) "CASA_JANELAS" id))
    (progn (cg:line (list (- (car a) h) (cadr a)) (list (- (car b) h) (cadr b)) "CASA_JANELAS" id)
     (cg:line (list (+ (car a) h) (cadr a)) (list (+ (car b) h) (cadr b)) "CASA_JANELAS" id))))
  (progn
   (setq hinge a)
   (if horiz
    (setq tip (list (car a) (+ (cadr a) width)) angle0 0.0 angle1 (/ pi 2.0))
    (progn
     (setq roomside (cg:find-id (cg:get "room_id" opening) (cg:get "rooms" *cg-drawing-model*)))
     (if (< (nth 0 (cg:get "bounds" roomside)) (car c))
      (setq tip (list (- (car a) width) (cadr a)) angle0 (/ pi 2.0) angle1 pi)
      (setq tip (list (+ (car a) width) (cadr a)) angle0 0.0 angle1 (/ pi 2.0)))))
   (cg:line hinge tip "CASA_PORTAS" id)
   (cg:mk (list '(0 . "ARC") '(8 . "CASA_PORTAS") (cons 10 (append hinge '(0.0)))
    (cons 40 width) (cons 50 angle0) (cons 51 angle1)) id))))
(defun cg:draw-furniture (item / box kind id)
 (setq box (cg:get "bounds" item) kind (cg:get "kind" item) id (cg:get "id" item))
 (cg:rect box "CASA_MOVEIS" id)
 (cond
  ((= kind "bed")
   (cg:rect (list (+ (nth 0 box) 100) (- (nth 3 box) 500) (- (nth 2 box) 100) (- (nth 3 box) 100)) "CASA_MOVEIS" id))
  ((= kind "sofa")
   (cg:rect (list (+ (nth 0 box) 100) (+ (nth 1 box) 100) (- (nth 2 box) 100) (- (nth 3 box) 200)) "CASA_MOVEIS" id))
  ((= kind "shower")
   (cg:line (list (nth 0 box) (nth 1 box)) (list (nth 2 box) (nth 3 box)) "CASA_MOVEIS" id))))
(defun cg:draw-model (model / site house walls openings rooms item box x0 y0 x1 y1 tx ty lineY i total clearbox ht wt it)
 (setq *cg-drawing-model* model site (cg:get "site_bounds" model) house (cg:get "house_bounds" model)
  walls (cg:get "walls" model) openings (cg:get "openings" model) rooms (cg:get "rooms" model)
  x0 (nth 0 house) y0 (nth 1 house) x1 (nth 2 house) y1 (nth 3 house))
 (foreach item '(("CASA_LOTE" 8) ("CASA_PAREDES" 7) ("CASA_PORTAS" 2) ("CASA_JANELAS" 4)
   ("CASA_MOVEIS" 3) ("CASA_TEXTOS" 7) ("CASA_COTAS" 6) ("CASA_ESTUDO" 8)) (cg:layer (car item) (cadr item)))
 (cg:rect site "CASA_LOTE" "SITE")
 (foreach item walls (cg:draw-wall item openings))
 (foreach item openings (cg:draw-opening item walls))
 (foreach item (cg:get "furniture" model) (cg:draw-furniture item))
 (foreach item rooms
  (setq box (cg:get "bounds" item))
  (if (/= (cg:get "kind" item) "corridor")
   (progn
    (cg:text (list (+ (nth 0 box) (if (> (nth 0 box) (/ (+ x0 x1) 2.0)) 1100 150)) (+ (nth 1 box) 350))
     (strcat (cg:get "id" item) " " (cg:get "name" item)) 150 "CASA_TEXTOS" (cg:get "id" item))
    (cg:text (list (+ (nth 0 box) (if (> (nth 0 box) (/ (+ x0 x1) 2.0)) 1100 150)) (+ (nth 1 box) 120))
     (strcat (rtos (cg:get "net_area_m2" item) 2 2) " m2") 120 "CASA_TEXTOS" (cg:get "id" item))
    (if (equal (nth 0 box) (+ x0 (cg:get "thickness" (car walls))) 0.01)
     (cg:dim (list (nth 0 box) (nth 1 box)) (list (nth 0 box) (nth 3 box))
      (list (- x0 600) (/ (+ (nth 1 box) (nth 3 box)) 2.0)) "DIM-ROOM")))))
 (foreach item (list (nth 0 rooms) (nth 1 rooms) (cg:find-id "CIRC" rooms))
  (setq box (cg:get "bounds" item))
  (cg:dim (list (nth 0 box) y0) (list (nth 2 box) y0)
   (list (nth 0 box) (- y0 450)) "DIM-CLEAR-W"))
 (cg:dim (list x0 y0) (list x1 y0) (list x0 (- y0 1000)) "DIM-HOUSE-W")
 (cg:dim (list x0 y0) (list x0 y1) (list (- x0 1300) y0) "DIM-HOUSE-D")
 (cg:dim (list (nth 0 site) (nth 1 site)) (list (nth 2 site) (nth 1 site))
  (list (nth 0 site) (- (nth 1 site) 1500)) "DIM-SITE-W")
 (cg:dim (list (nth 2 site) (nth 1 site)) (list (nth 2 site) (nth 3 site))
  (list (+ (nth 2 site) 1200) (nth 1 site)) "DIM-SITE-D")
 (setq tx (+ (nth 2 site) 3500) ty (nth 3 site) lineY (- ty 800) total 0.0)
 (cg:text (list tx ty) "CASA BH | ESTUDO PRELIMINAR" 300 "CASA_TEXTOS" "TITLE")
 (cg:text (list tx (- ty 450)) (strcat "Projeto " (cg:get "project_id" model) " | seed " (itoa (fix (cg:get "seed" model)))) 180 "CASA_TEXTOS" "TITLE")
 (foreach item rooms
  (cg:text (list tx lineY) (strcat (cg:get "id" item) " - " (cg:get "name" item) " : "
    (rtos (cg:get "net_area_m2" item) 2 2) " m2") 180 "CASA_TEXTOS" "SCHEDULE")
  (setq lineY (- lineY 320) total (+ total (cg:get "net_area_m2" item))))
 (cg:text (list tx (- lineY 150)) (strcat "Area util: " (rtos total 2 2) " m2 | Construida geometrica: "
   (rtos (cg:get "gross_area_m2" model) 2 2) " m2") 180 "CASA_TEXTOS" "SCHEDULE")
 (setq lineY (- lineY 600))
 (foreach item '("Nao aprovado pela PBH. Faixas livres sao parametros de ensaio."
   "Cotas em metros; geometria em milimetros. Terreno plano hipotetico."
   "Norte, levantamento, cobertura, estrutura e instalacoes: a definir."
   "Mobiliario esquematico. Operacao e acessibilidade nao verificadas."
   "Revit: exportar snapshot gerado; alteracoes manuais CAD nao seguem.")
  (cg:text (list tx lineY) item 160 "CASA_TEXTOS" "NOTES") (setq lineY (- lineY 300)))
 ;; Schematic section and facade, deliberately not construction details.
 (setq lineY (- lineY 4500) ht (cg:get "height" (car walls)) wt (cg:get "thickness" (car walls)) it (cg:opt "wall_internal" model wt))
 (cg:text (list tx (+ lineY ht 550)) "CORTE A-A ESQUEMATICO | cobertura a definir" 220 "CASA_TEXTOS" "SECTION")
 (cg:rect (list tx (- lineY 150) (+ tx (- x1 x0)) lineY) "CASA_ESTUDO" "SECTION")
 (cg:rect (list tx lineY (+ tx wt) (+ lineY ht)) "CASA_ESTUDO" "SECTION")
 (cg:rect (list (- (+ tx (- x1 x0)) wt) lineY (+ tx (- x1 x0)) (+ lineY ht)) "CASA_ESTUDO" "SECTION")
 (setq clearbox (cg:get "bounds" (cg:find-id "CIRC" rooms)))
 (cg:rect (list (+ tx (- (nth 0 clearbox) x0 it)) lineY (+ tx (- (nth 0 clearbox) x0)) (+ lineY ht)) "CASA_ESTUDO" "SECTION")
 (cg:rect (list (+ tx (- (nth 2 clearbox) x0)) lineY (+ tx (- (nth 2 clearbox) x0) it) (+ lineY ht)) "CASA_ESTUDO" "SECTION")
 (cg:line (list tx (+ lineY ht)) (list (+ tx (- x1 x0)) (+ lineY ht)) "CASA_ESTUDO" "SECTION")
 (cg:dim (list tx lineY) (list tx (+ lineY ht)) (list (- tx 650) lineY) "DIM-HEIGHT")
 (cg:line (list (- x0 300) (+ y0 1600)) (list (+ x1 300) (+ y0 1600)) "CASA_ESTUDO" "SECTION-MARK")
 (cg:text (list (- x0 350) (+ y0 1850)) "A" 200 "CASA_TEXTOS" "SECTION-MARK")
 (cg:text (list (+ x1 200) (+ y0 1850)) "A" 200 "CASA_TEXTOS" "SECTION-MARK")
 (setq lineY (- lineY 5000))
 (cg:text (list tx (+ lineY ht 550)) "FACHADA FRONTAL ESQUEMATICA" 220 "CASA_TEXTOS" "FACADE")
 (cg:rect (list tx lineY (+ tx (- x1 x0)) (+ lineY ht)) "CASA_ESTUDO" "FACADE")
 (cg:rect (list (+ tx (/ (- (- x1 x0) 900) 2.0)) lineY
  (+ tx (/ (+ (- x1 x0) 900) 2.0)) (+ lineY 2100)) "CASA_ESTUDO" "FACADE")
 (princ))
(defun cg:store-model (model / dictionary entry str chunks i record)
 (setq entry (dictsearch (namedobjdict) "CASA_BH_MODELS"))
 (if entry (setq dictionary (cdr (assoc -1 entry)))
  (progn (setq dictionary (entmakex '((0 . "DICTIONARY") (100 . "AcDbDictionary") (281 . 1))))
   (dictadd (namedobjdict) "CASA_BH_MODELS" dictionary)))
 (setq str (cg:json model) chunks nil i 1)
 (while (<= i (strlen str)) (setq chunks (append chunks (list (cons 1 (substr str i 240))))) (setq i (+ i 240)))
 (setq record (entmakex (append '((0 . "XRECORD") (100 . "AcDbXrecord") (280 . 1)) chunks)))
 (if (not (dictadd dictionary (cg:get "project_id" model) record))
  (progn (princ "\nFalha ao gravar snapshot do projeto.") (exit))))
(defun cg:restore-vars (values / pair)
 (foreach pair values (setvar (car pair) (cdr pair))))
(defun cg:commit (model / *error* saved undoStarted ucsChanged key *cg-pid* *cg-drawing-model*)
 (setq saved nil undoStarted nil ucsChanged nil *cg-pid* (cg:get "project_id" model))
 (foreach key '("CMDECHO" "OSMODE" "CLAYER" "DIMTXT" "DIMASZ" "DIMSCALE" "DIMDEC" "DIMLUNIT" "DIMLFAC" "DIMZIN" "DIMPOST" "DIMTAD" "DIMTIH" "DIMTOH" "DIMGAP" "DIMEXE" "DIMEXO" "DIMTSZ")
  (setq saved (cons (cons key (getvar key)) saved)))
 (defun *error* (message)
  (if ucsChanged (command-s "_.UCS" "_Previous"))
  (cg:restore-vars saved)
  (if undoStarted (progn (command-s "_.UNDO" "_End") (command-s "_.U")))
  (princ (strcat "\nGeracao cancelada: " message)) (princ))
 (if (or (/= (getvar "INSUNITS") 4) (/= (getvar "TILEMODE") 1))
  (progn (princ "\nUse a aba Modelo e desenho em milimetros (INSUNITS=4). Nenhuma entidade criada.") nil)
  (progn
   (command-s "_.UNDO" "_Begin") (setq undoStarted T)
   (command-s "_.UCS" "_World") (setq ucsChanged T)
   (regapp "CASA_BH")
   (setvar "CMDECHO" 0) (setvar "OSMODE" 0)
   (setvar "DIMTXT" 140) (setvar "DIMASZ" 120) (setvar "DIMSCALE" 1.0)
   (setvar "DIMDEC" 2) (setvar "DIMLUNIT" 2) (setvar "DIMLFAC" 0.001)
   (setvar "DIMZIN" 0) (setvar "DIMPOST" "<>")
   (setvar "DIMTAD" 1) (setvar "DIMTIH" 0) (setvar "DIMTOH" 0)
   (setvar "DIMGAP" 60) (setvar "DIMEXE" 100) (setvar "DIMEXO" 80) (setvar "DIMTSZ" 70)
   (cg:draw-model model) (cg:store-model model)
   (command-s "_.UCS" "_Previous") (setq ucsChanged nil)
   (cg:restore-vars saved)
   (command-s "_.UNDO" "_End") (setq undoStarted nil)
   (setq *casa-last* model) T)))
(defun c:CASA_GERAR (/ origin model params pid)
 (if (and (cg:ensure-core) (cg:form))
  (progn
   (setq origin (getpoint "\nPonto de insercao do canto frontal esquerdo do lote: "))
   (if origin
    (progn
     (setq origin (trans origin 1 0) pid (strcat "CG-" (rtos (getvar "CDATE") 2 8) "-" (itoa (getvar "MILLISECS"))))
     (setq params (append *casa-params* (list (cons "origin_x" (car origin)) (cons "origin_y" (cadr origin)) (cons "project_id" pid))))
     (setq model (cg:generate params))
     (if (cg:get "error" model) (alert (cg:get "error" model))
      (if (cg:commit model)
       (princ "\nPlanta criada. ZOOM Extents para visualizar. CASA_EXPORTAR envia o snapshot para JSON/Revit.")))))))
 (princ))
(defun cg:stored-json (pid / entry dictionary row result)
 (setq entry (dictsearch (namedobjdict) "CASA_BH_MODELS") result nil)
 (if entry
  (progn (setq dictionary (cdr (assoc -1 entry)) entry (dictsearch dictionary pid))
   (if entry (progn (setq result "") (foreach row entry (if (= (car row) 1) (setq result (strcat result (cdr row))))))))) result)
(defun c:CASA_EXPORTAR (/ selection entity xd pid snapshot file stream)
 (setq selection (entsel "\nSelecione uma entidade da planta gerada (Enter = ultimo projeto nesta sessao): "))
 (if selection
  (progn (setq entity (car selection) xd (assoc -3 (entget entity '("CASA_BH"))))
   (if xd (setq pid (cdr (assoc 1000 (cdr (cadr xd)))))))
  (if *casa-last* (setq pid (cg:get "project_id" *casa-last*))))
 (if pid (setq snapshot (cg:stored-json pid)))
 (if snapshot
  (progn
   (setq file (getfiled "Exportar snapshot gerado - edicoes manuais nao incluidas" (strcat (getvar "DWGPREFIX") pid ".json") "json" 1))
   (if file
    (progn (setq stream (open file "w"))
     (if stream (progn (write-line snapshot stream) (close stream) (princ (strcat "\nJSON salvo: " file)))
      (alert "Nao foi possivel gravar o arquivo.")))))
  (alert "Nenhum snapshot encontrado. Selecione uma entidade CASA_BH gerada neste desenho."))
 (princ))
(defun c:CASA_AJUDA ()
 (alert "CASA_GERAR: formulario e planta. CASA_EXPORTAR: JSON para Dynamo/Revit.\nLeia README.md. Estudo preliminar em lote hipotetico; nao e projeto aprovado.\nEdicoes manuais nao atualizam o JSON. Para outra alternativa, altere a semente e gere em outro ponto.") (princ))
(princ "\nCASA BH carregado. Comandos: CASA_GERAR, CASA_EXPORTAR, CASA_AJUDA.")
(princ)
