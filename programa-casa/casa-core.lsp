;;; CASA BH 0.1 - geometric core. All lengths in millimetres.
;;; Pure AutoLISP. Numerical sizes below are prototype design choices, NOT law.
(defun cg:get (key data) (cdr (assoc key data)))
(defun cg:opt (key data fallback / val)
  (setq val (cg:get key data)) (if val val fallback))
(defun cg:wall-thickness (key params)
  (cg:opt key params (cg:get "wall" params)))
(defun cg:point (x y) (list x y))
(defun cg:rand (/ next)
  (setq next (fix (rem (* 48271.0 *cg-seed*) 2147483647.0)))
  (setq *cg-seed* (if (> next 0) next 1))
  (/ *cg-seed* 2147483647.0))
(defun cg:drop-nth (idx items / out pos item)
  (setq out nil pos 0)
  (foreach item items (if (/= pos idx) (setq out (cons item out))) (setq pos (1+ pos)))
  (reverse out))
(defun cg:shuffle (items / out idx)
  (setq out nil)
  (while items
    (setq idx (fix (* (length items) (cg:rand))))
    (setq out (cons (nth idx items) out) items (cg:drop-nth idx items)))
  (reverse out))
(defun cg:add-wall (a b thick height / existing wall id)
  (setq existing nil)
  (foreach wall *cg-walls*
    (if (or (and (equal a (cg:get "start" wall) 0.01) (equal b (cg:get "end" wall) 0.01))
            (and (equal b (cg:get "start" wall) 0.01) (equal a (cg:get "end" wall) 0.01)))
      (setq existing (cg:get "id" wall))))
  (if existing existing
    (progn
      (setq id (strcat "W" (itoa (1+ (length *cg-walls*)))))
      (setq *cg-walls* (append *cg-walls* (list (list (cons "id" id)
        (cons "start" a) (cons "end" b) (cons "thickness" thick) (cons "height" height)
        (cons "wall_role" (if *cg-wall-role* *cg-wall-role* "internal")))))) id)))
(defun cg:add-opening (wall kind center width height sill room / id)
  (setq id (strcat "O" (itoa (1+ (length *cg-openings*)))))
  (setq *cg-openings* (append *cg-openings* (list (list
    (cons "id" id) (cons "wall_id" wall) (cons "kind" kind)
    (cons "center" center) (cons "width" width) (cons "height" height)
    (cons "sill" sill) (cons "room_id" room))))) id)
(defun cg:add-furniture (kind bounds height room / id)
  (setq id (strcat "F" (itoa (1+ (length *cg-furniture*)))))
  (setq *cg-furniture* (append *cg-furniture* (list (list
    (cons "id" id) (cons "kind" kind) (cons "bounds" bounds)
    (cons "height" height) (cons "room_id" room))))))
(defun cg:furnish (room / box x0 y0 x1 y1 kind id width)
  (setq box (cg:get "bounds" room) x0 (nth 0 box) y0 (nth 1 box)
        x1 (nth 2 box) y1 (nth 3 box) kind (cg:get "kind" room)
        id (cg:get "id" room) width (- x1 x0))
  (cond
    ((= kind "bedroom")
      (cg:add-furniture "bed" (list (+ x0 150) (- y1 2100) (+ x0 1750) (- y1 100)) 550 id)
      (if (>= width 3000)
        (cg:add-furniture "wardrobe" (list (- x1 750) (- y1 1700) (- x1 150) (- y1 150)) 2200 id)))
    ((= kind "living")
      (cg:add-furniture "sofa" (list (+ x0 150) (- y1 1050) (+ x0 2350) (- y1 150)) 850 id))
    ((= kind "kitchen")
      (cg:add-furniture "fridge" (list (+ x0 100) (- y1 850) (+ x0 800) (- y1 100)) 1800 id)
      (cg:add-furniture "counter" (list (+ x0 1000) (- y1 700) (- x1 100) (- y1 100)) 900 id))
    ((= kind "bathroom")
      (cg:add-furniture "toilet" (list (+ x0 100) (- y1 900) (+ x0 800) (- y1 100)) 700 id)
      (cg:add-furniture "basin" (list (+ x0 950) (- y1 550) (+ x0 1550) (- y1 100)) 850 id)
      (cg:add-furniture "shower" (list (- x1 1000) (- y1 1000) (- x1 100) (- y1 100)) 100 id))
    ((= kind "laundry")
      (cg:add-furniture "washer" (list (+ x0 150) (- y1 800) (+ x0 750) (- y1 150)) 900 id))
    ((= kind "dining")
      (cg:add-furniture "table" (list (+ x0 500) (- y1 1400) (+ x0 1900) (- y1 600)) 750 id))
    ((= kind "office")
      (cg:add-furniture "desk" (list (+ x0 150) (- y1 750) (+ x0 1350) (- y1 150)) 750 id))))
(defun cg:validate-input (params / err key val total ti te)
  (setq err nil total 0 ti (cg:wall-thickness "wall_internal" params)
        te (cg:wall-thickness "wall_external" params))
  (if (not (and (numberp ti) (numberp te)))
    (setq err "Informe espessuras wall_internal e wall_external ou wall legado."))
  (foreach key '("lot_width" "lot_depth" "front" "rear" "side" "corridor" "house_width" "height" "seed")
    (setq val (cg:get key params))
    (if (not (numberp val)) (setq err (strcat "Campo numerico ausente: " key))))
  (foreach key '("bedrooms" "bathrooms" "living" "kitchens" "laundry" "dining" "office")
    (setq val (cg:get key params))
    (if (or (not (numberp val)) (< val 0) (/= val (fix val)) (> val 8))
      (setq err (strcat "Quantidade invalida (0 a 8): " key))
      (setq total (+ total val))))
  (if (not err)
    (cond
      ((or (< (cg:get "bedrooms" params) 1) (< (cg:get "bathrooms" params) 1)
           (< (cg:get "living" params) 1) (< (cg:get "kitchens" params) 1))
        (setq err "MVP exige ao menos 1 quarto, banheiro, sala e cozinha."))
      ((> total 20) (setq err "Limite do prototipo: 20 ambientes solicitados."))
      ((or (< (cg:get "lot_width" params) 7000) (> (cg:get "lot_width" params) 200000)
           (< (cg:get "lot_depth" params) 7000) (> (cg:get "lot_depth" params) 200000))
        (setq err "Lote deve medir entre 7 e 200 metros em cada direcao."))
      ((or (< (cg:get "front" params) 0) (< (cg:get "rear" params) 0) (< (cg:get "side" params) 0))
        (setq err "Faixas livres nao podem ser negativas."))
      ((or (< ti 100) (> ti 300) (< te 100) (> te 300)
           (< (cg:get "corridor" params) 1000) (> (cg:get "corridor" params) 2000)
           (< (cg:get "height" params) 2400) (> (cg:get "height" params) 4000))
        (setq err "Perfil de ensaio: parede 0.10-0.30m; corredor 1-2m; altura 2.40-4m."))
      ((or (< (cg:get "seed" params) 1) (> (cg:get "seed" params) 2147483646)
           (/= (cg:get "seed" params) (fix (cg:get "seed" params))))
        (setq err "Semente deve ser inteiro de 1 a 2147483646."))
      ((or (> (cg:get "house_width" params) (- (cg:get "lot_width" params) (* 2 (cg:get "side" params))))
           (< (/ (- (cg:get "house_width" params) (cg:get "corridor" params) (* 2 ti) (* 2 te)) 2.0) 2600))
        (setq err "Largura da casa nao cabe nas faixas ou deixa ambientes menores que 2.60m."))))
  err)
(defun cg:generate (params / error *cg-walls* *cg-openings* *cg-furniture* *cg-seed* *cg-wall-role*
  program spec count idx entry rows row depth depths required tWall tExt height cw x0 x1 y0 yEnd
  xa xb ca cb leftAxis rightAxis current nextY west east item room box rooms nrow side
  wallId exteriorLeft exteriorRight exteriorFront exteriorBack roomId centerY windowW
  corridorEnd corridorRoom ox oy totalArea checks lowerThick upperThick clearY0 clearY1)
  (setq error (cg:validate-input params))
  (if error (list (cons "error" error))
    (progn
      (setq *cg-walls* nil *cg-openings* nil *cg-furniture* nil *cg-seed* (cg:get "seed" params)
        program nil rooms nil rows nil tWall (cg:wall-thickness "wall_internal" params)
        tExt (cg:wall-thickness "wall_external" params) height (cg:get "height" params)
        cw (cg:get "corridor" params) ox (cg:opt "origin_x" params 0.0) oy (cg:opt "origin_y" params 0.0))
      (foreach spec '(("bedrooms" "bedroom" "Quarto" 3200) ("bathrooms" "bathroom" "Banheiro" 2200)
        ("living" "living" "Sala" 3600) ("kitchens" "kitchen" "Cozinha" 3000)
        ("laundry" "laundry" "Lavanderia" 2200) ("dining" "dining" "Jantar" 3000)
        ("office" "office" "Escritorio" 2800))
        (setq idx 1 count (fix (cg:get (nth 0 spec) params)))
        (repeat count
          (setq program (append program (list (list (cons "kind" (nth 1 spec))
            (cons "name" (strcat (nth 2 spec) " " (itoa idx))) (cons "depth" (nth 3 spec))))))
          (setq idx (1+ idx))))
      (setq program (cg:shuffle program) required (- (* 2 tExt) tWall))
      (while program
        (setq west (car program) program (cdr program) east (car program) program (cdr program)
          depth (+ (max (cg:get "depth" west) (if east (cg:get "depth" east) 0)) (* 100 (fix (* 4 (cg:rand))))))
        (setq rows (append rows (list (list west east depth))) required (+ required depth tWall)))
      (if (> required (- (cg:get "lot_depth" params) (cg:get "front" params) (cg:get "rear" params)))
        (list (cons "error" (strcat "Nao foi encontrado encaixe nesta tipologia/semente. Profundidade requerida: "
          (rtos (/ required 1000.0) 2 2) "m. Aumente o lote, altere o programa ou tente outra semente.")))
        (progn
          (setq x0 (+ ox (cg:get "side" params)) x1 (+ x0 (cg:get "house_width" params))
            y0 (+ oy (cg:get "front" params)) yEnd (+ y0 required)
            xa (+ x0 (/ tExt 2.0)) xb (- x1 (/ tExt 2.0))
            ca (/ (- (+ x0 x1) cw) 2.0) cb (+ ca cw)
            leftAxis (- ca (/ tWall 2.0)) rightAxis (+ cb (/ tWall 2.0))
            current (+ y0 (/ tExt 2.0)) corridorEnd (- yEnd tExt)
            *cg-wall-role* "external")
          (setq exteriorFront (cg:add-wall (list xa current) (list xb current) tExt height)
            exteriorBack (cg:add-wall (list xa (- yEnd (/ tExt 2.0))) (list xb (- yEnd (/ tExt 2.0))) tExt height)
            exteriorLeft (cg:add-wall (list xa current) (list xa (- yEnd (/ tExt 2.0))) tExt height)
            exteriorRight (cg:add-wall (list xb current) (list xb (- yEnd (/ tExt 2.0))) tExt height)
            *cg-wall-role* "internal")
          (cg:add-opening exteriorFront "door" (list (/ (+ ca cb) 2.0) current) 900 2100 0 "CIRC")
          (setq nrow 0)
          (foreach row rows
            (setq west (nth 0 row) east (nth 1 row) depth (nth 2 row)
              lowerThick (if (= nrow 0) tExt tWall)
              upperThick (if (= nrow (1- (length rows))) tExt tWall)
              clearY0 (+ current (/ lowerThick 2.0)) clearY1 (+ clearY0 depth)
              nextY (+ clearY1 (/ upperThick 2.0)))
            (if east
              (progn
                (if (> nrow 0)
                  (progn (cg:add-wall (list xa current) (list leftAxis current) tWall height)
                    (cg:add-wall (list rightAxis current) (list xb current) tWall height)))
                (setq side 0)
                (foreach item (list west east)
                  (setq roomId (strcat "R" (itoa (1+ (length rooms)))))
                  (if (= side 0)
                    (setq box (list (+ x0 tExt) clearY0 (- ca tWall) clearY1)
                      wallId (cg:add-wall (list leftAxis current) (list leftAxis nextY) tWall height))
                    (setq box (list (+ cb tWall) clearY0 (- x1 tExt) clearY1)
                      wallId (cg:add-wall (list rightAxis current) (list rightAxis nextY) tWall height)))
                  (setq room (list (cons "id" roomId) (cons "name" (cg:get "name" item))
                    (cons "kind" (cg:get "kind" item)) (cons "bounds" box)
                    (cons "net_area_m2" (/ (* (- (nth 2 box) (nth 0 box)) (- (nth 3 box) (nth 1 box))) 1000000.0))))
                  (setq rooms (append rooms (list room)))
                  (cg:add-opening wallId "door" (list (if (= side 0) leftAxis rightAxis) (+ clearY0 650)) 800 2100 0 roomId)
                  (setq windowW (if (= (cg:get "kind" item) "bathroom") 600 1200))
                  (cg:add-opening (if (= side 0) exteriorLeft exteriorRight) "window"
                    (list (if (= side 0) xa xb) (/ (+ clearY0 clearY1) 2.0))
                    windowW (if (= windowW 600) 600 1000) (if (= windowW 600) 1600 1100) roomId)
                  (if (= (cg:get "furniture" params) 1) (cg:furnish room))
                  (setq side (1+ side))))
              (progn
                (setq corridorEnd (- current (/ tWall 2.0)) roomId (strcat "R" (itoa (1+ (length rooms)))))
                (setq wallId (cg:add-wall (list xa current) (list xb current) tWall height))
                (cg:add-opening wallId "door" (list (/ (+ ca cb) 2.0) current) 900 2100 0 roomId)
                (setq box (list (+ x0 tExt) clearY0 (- x1 tExt) clearY1))
                (setq room (list (cons "id" roomId) (cons "name" (cg:get "name" west))
                  (cons "kind" (cg:get "kind" west)) (cons "bounds" box)
                  (cons "net_area_m2" (/ (* (- (nth 2 box) (nth 0 box)) (- (nth 3 box) (nth 1 box))) 1000000.0))))
                (setq rooms (append rooms (list room)))
                (cg:add-opening exteriorBack "window" (list (/ (+ x0 x1) 2.0) (- yEnd (/ tExt 2.0))) 1200 1000 1100 roomId)
                (if (= (cg:get "furniture" params) 1) (cg:furnish room))))
            (setq current nextY nrow (1+ nrow)))
          (setq corridorRoom (list (cons "id" "CIRC") (cons "name" "Circulacao") (cons "kind" "corridor")
            (cons "bounds" (list ca (+ y0 tExt) cb corridorEnd))
            (cons "net_area_m2" (/ (* cw (- corridorEnd (+ y0 tExt))) 1000000.0))))
          (setq rooms (append rooms (list corridorRoom)) totalArea (/ (* (- x1 x0) (- yEnd y0)) 1000000.0))
          (list (cons "schema_version" "1.0") (cons "project_id" (cg:opt "project_id" params "CG-DEMO"))
            (cons "units" "mm") (cons "origin" (list ox oy 0.0)) (cons "algorithm_version" "corridor-0.1")
            (cons "seed" (cg:get "seed" params)) (cons "site_mode" "hypothetical_flat")
            (cons "site_bounds" (list ox oy (+ ox (cg:get "lot_width" params)) (+ oy (cg:get "lot_depth" params))))
            (cons "house_bounds" (list x0 y0 x1 yEnd)) (cons "gross_area_m2" totalArea)
            (cons "wall_internal" tWall) (cons "wall_external" tExt)
            (cons "walls" *cg-walls*) (cons "openings" *cg-openings*) (cons "rooms" rooms)
            (cons "furniture" *cg-furniture*)
            (cons "slab" (list (cons "bounds" (list x0 y0 x1 yEnd)) (cons "thickness" 150)))
            (cons "validations" (list
              (list (cons "rule_id" "PROGRAM") (cons "status" "pass") (cons "message" "Quantidades geradas conforme entrada; circulacao acrescentada."))
              (list (cons "rule_id" "BH") (cons "status" "not_evaluated") (cons "message" "Lote hipotetico; faixas de ensaio nao sao parametros municipais."))
              (list (cons "rule_id" "COMFORT") (cons "status" "not_evaluated") (cons "message" "Conforto, acessibilidade e operacao de mobiliario requerem verificacao."))))))))))
(princ)
