;;; CASA BH 0.1 - geometric core. All lengths in millimetres.
;;; Pure AutoLISP. Numerical sizes below are prototype design choices, NOT law.
(defun cg:get (key data) (cdr (assoc key data)))
(defun cg:opt (key data fallback / val)
  (setq val (cg:get key data)) (if val val fallback))
(defun cg:wall-thickness (key params)
  (cg:opt key params (cg:get "wall" params)))
(defun cg:point (x y) (list x y))
(defun cg:rand (/ next)
  (setq next (fix (rem (* 48271.0 *cg-seed*) 2147483647.0)))
  (setq *cg-seed* (if (> next 0) next 1))
  (/ *cg-seed* 2147483647.0))
(defun cg:drop-nth (idx items / out pos item)
  (setq out nil pos 0)
  (foreach item items (if (/= pos idx) (setq out (cons item out))) (setq pos (1+ pos)))
  (reverse out))
(defun cg:shuffle (items / out idx)
  (setq out nil)
  (while items
    (setq idx (fix (* (length items) (cg:rand))))
    (setq out (cons (nth idx items) out) items (cg:drop-nth idx items)))
  (reverse out))
(defun cg:add-wall (a b thick height / existing wall id)
  (setq existing nil)
  (foreach wall *cg-walls*
    (if (or (and (equal a (cg:get "start" wall) 0.01) (equal b (cg:get "end" wall) 0.01))
            (and (equal b (cg:get "start" wall) 0.01) (equal a (cg:get "end" wall) 0.01)))
      (setq existing (cg:get "id" wall))))
  (if existing existing
    (progn
      (setq id (strcat "W" (itoa (1+ (length *cg-walls*)))))
      (setq *cg-walls* (append *cg-walls* (list (list (cons "id" id)
        (cons "start" a) (cons "end" b) (cons "thickness" thick) (cons "height" height)
        (cons "wall_role" (if *cg-wall-role* *cg-wall-role* "internal")))))) id)))
(defun cg:add-opening (wall kind center width height sill room / id)
  (setq id (strcat "O" (itoa (1+ (length *cg-openings*)))))
  (setq *cg-openings* (append *cg-openings* (list (list
    (cons "id" id) (cons "wall_id" wall) (cons "kind" kind)
    (cons "center" center) (cons "width" width) (cons "height" height)
    (cons "sill" sill) (cons "room_id" room))))) id)
(defun cg:add-furniture (kind bounds height room / id)
  (setq id (strcat "F" (itoa (1+ (length *cg-furniture*)))))
  (setq *cg-furniture* (append *cg-furniture* (list (list
    (cons "id" id) (cons "kind" kind) (cons "bounds" bounds)
    (cons "height" height) (cons "room_id" room))))))
(defun cg:furnish (room / box x0 y0 x1 y1 kind id width)
  (setq box (cg:get "bounds" room) x0 (nth 0 box) y0 (nth 1 box)
        x1 (nth 2 box) y1 (nth 3 box) kind (cg:get "kind" room)
        id (cg:get "id" room) width (- x1 x0))
  (cond
    ((= kind "bedroom")
      (cg:add-furniture "bed" (list (+ x0 150) (- y1 2100) (+ x0 1750) (- y1 100)) 550 id)
      (if (>= width 3000)
        (cg:add-furniture "wardrobe" (list (- x1 750) (- y1 1700) (- x1 150) (- y1 150)) 2200 id)))
    ((= kind "living")
      (cg:add-furniture "sofa" (list (+ x0 150) (- y1 1050) (+ x0 2350) (- y1 150)) 850 id))
    ((= kind "kitchen")
      (cg:add-furniture "fridge" (list (+ x0 100) (- y1 850) (+ x0 800) (- y1 100)) 1800 id)
      (cg:add-furniture "counter" (list (+ x0 1000) (- y1 700) (- x1 100) (- y1 100)) 900 id))
    ((= kind "bathroom")
      (cg:add-furniture "toilet" (list (+ x0 100) (- y1 900) (+ x0 800) (- y1 100)) 700 id)
      (cg:add-furniture "basin" (list (+ x0 950) (- y1 550) (+ x0 1550) (- y1 100)) 850 id)
      (cg:add-furniture "shower" (list (- x1 1000) (- y1 1000) (- x1 100) (- y1 100)) 100 id))
    ((= kind "laundry")
      (cg:add-furniture "washer" (list (+ x0 150) (- y1 800) (+ x0 750) (- y1 150)) 900 id))
    ((= kind "dining")
      (cg:add-furniture "table" (list (+ x0 500) (- y1 1400) (+ x0 1900) (- y1 600)) 750 id))
    ((= kind "office")
      (cg:add-furniture "desk" (list (+ x0 150) (- y1 750) (+ x0 1350) (- y1 150)) 750 id))))
(defun cg:validate-input (params / err key val total ti te)
  (setq err nil total 0 ti (cg:wall-thickness "wall_internal" params)
        te (cg:wall-thickness "wall_external" params))
  (if (not (and (numberp ti) (numberp te)))
    (setq err "Informe espessuras wall_internal e wall_external ou wall legado."))
  (foreach key '("lot_width" "lot_depth" "front" "rear" "side" "corridor" "house_width" "height" "seed")
    (setq val (cg:get key params))
    (if (not (numberp val)) (setq err (strcat "Campo numerico ausente: " key))))
  (foreach key '("bedrooms" "bathrooms" "living" "kitchens" "laundry" "dining" "office")
    (setq val (cg:get key params))
    (if (or (not (numberp val)) (< val 0) (/= val (fix val)) (> val 8))
      (setq err (strcat "Quantidade invalida (0 a 8): " key))
      (setq total (+ total val))))
  (if (not err)
    (cond
      ((or (< (cg:get "bedrooms" params) 1) (< (cg:get "bathrooms" params) 1)
           (< (cg:get "living" params) 1) (< (cg:get "kitchens" params) 1))
        (setq err "MVP exige ao menos 1 quarto, banheiro, sala e cozinha."))
      ((> total 20) (setq err "Limite do prototipo: 20 ambientes solicitados."))
      ((or (< (cg:get "lot_width" params) 7000) (> (cg:get "lot_width" params) 200000)
           (< (cg:get "lot_depth" params) 7000) (> (cg:get "lot_depth" params) 200000))
        (setq err "Lote deve medir entre 7 e 200 metros em cada direcao."))
      ((or (< (cg:get "front" params) 0) (< (cg:get "rear" params) 0) (< (cg:get "side" params) 0))
        (setq err "Faixas livres nao podem ser negativas."))
      ((or (< ti 100) (> ti 300) (< te 100) (> te 300)
           (< (cg:get "corridor" params) 1000) (> (cg:get "corridor" params) 2000)
           (< (cg:get "height" params) 2400) (> (cg:get "height" params) 4000))
        (setq err "Perfil de ensaio: parede 0.10-0.30m; corredor 1-2m; altura 2.40-4m."))
      ((or (< (cg:get "seed" params) 1) (> (cg:get "seed" params) 2147483646)
           (/= (cg:get "seed" params) (fix (cg:get "seed" params))))
        (setq err "Semente deve ser inteiro de 1 a 2147483646."))
      ((or (> (cg:get "house_width" params) (- (cg:get "lot_width" params) (* 2 (cg:get "side" params))))
           (< (/ (- (cg:get "house_width" params) (cg:get "corridor" params) (* 2 ti) (* 2 te)) 2.0) 2600))
        (setq err "Largura da casa nao cabe nas faixas ou deixa ambientes menores que 2.60m."))))
  err)
(defun cg:generate (params / error *cg-walls* *cg-openings* *cg-furniture* *cg-seed* *cg-wall-role*
  program spec count idx entry rows row depth depths required tWall tExt height cw x0 x1 y0 yEnd
  xa xb ca cb leftAxis rightAxis current nextY west east item room box rooms nrow side
  wallId exteriorLeft exteriorRight exteriorFront exteriorBack roomId centerY windowW
  corridorEnd corridorRoom ox oy totalArea checks lowerThick upperThick clearY0 clearY1)
  (setq error (cg:validate-input params))
  (if error (list (cons "error" error))
    (progn
      (setq *cg-walls* nil *cg-openings* nil *cg-furniture* nil *cg-seed* (cg:get "seed" params)
        program nil rooms nil rows nil tWall (cg:wall-thickness "wall_internal" params)
        tExt (cg:wall-thickness "wall_external" params) height (cg:get "height" params)
        cw (cg:get "corridor" params) ox (cg:opt "origin_x" params 0.0) oy (cg:opt "origin_y" params 0.0))
      (foreach spec '(("bedrooms" "bedroom" "Quarto" 3200) ("bathrooms" "bathroom" "Banheiro" 2200)
        ("living" "living" "Sala" 3600) ("kitchens" "kitchen" "Cozinha" 3000)
        ("laundry" "laundry" "Lavanderia" 2200) ("dining" "dining" "Jantar" 3000)
        ("office" "office" "Escritorio" 2800))
        (setq idx 1 count (fix (cg:get (nth 0 spec) params)))
        (repeat count
          (setq program (append program (list (list (cons "kind" (nth 1 spec))
            (cons "name" (strcat (nth 2 spec) " " (itoa idx))) (cons "depth" (nth 3 spec))))))
          (setq idx (1+ idx))))
      (setq program (cg:shuffle program) required (- (* 2 tExt) tWall))
      (while program
        (setq west (car program) program (cdr program) east (car program) program (cdr program)
          depth (+ (max (cg:get "depth" west) (if east (cg:get "depth" east) 0)) (* 100 (fix (* 4 (cg:rand))))))
        (setq rows (append rows (list (list west east depth))) required (+ required depth tWall)))
      (if (> required (- (cg:get "lot_depth" params) (cg:get "front" params) (cg:get "rear" params)))
        (list (cons "error" (strcat "Nao foi encontrado encaixe nesta tipologia/semente. Profundidade requerida: "
          (rtos (/ required 1000.0) 2 2) "m. Aumente o lote, altere o programa ou tente outra semente.")))
        (progn
          (setq x0 (+ ox (cg:get "side" params)) x1 (+ x0 (cg:get "house_width" params))
            y0 (+ oy (cg:get "front" params)) yEnd (+ y0 required)
            xa (+ x0 (/ tExt 2.0)) xb (- x1 (/ tExt 2.0))
            ca (/ (- (+ x0 x1) cw) 2.0) cb (+ ca cw)
            leftAxis (- ca (/ tWall 2.0)) rightAxis (+ cb (/ tWall 2.0))
            current (+ y0 (/ tExt 2.0)) corridorEnd (- yEnd tExt)
            *cg-wall-role* "external")
          (setq exteriorFront (cg:add-wall (list xa current) (list xb current) tExt height)
            exteriorBack (cg:add-wall (list xa (- yEnd (/ tExt 2.0))) (list xb (- yEnd (/ tExt 2.0))) tExt height)
            exteriorLeft (cg:add-wall (list xa current) (list xa (- yEnd (/ tExt 2.0))) tExt height)
            exteriorRight (cg:add-wall (list xb current) (list xb (- yEnd (/ tExt 2.0))) tExt height)
            *cg-wall-role* "internal")
          (cg:add-opening exteriorFront "door" (list (/ (+ ca cb) 2.0) current) 900 2100 0 "CIRC")
          (setq nrow 0)
          (foreach row rows
            (setq west (nth 0 row) east (nth 1 row) depth (nth 2 row)
              lowerThick (if (= nrow 0) tExt tWall)
              upperThick (if (= nrow (1- (length rows))) tExt tWall)
              clearY0 (+ current (/ lowerThick 2.0)) clearY1 (+ clearY0 depth)
              nextY (+ clearY1 (/ upperThick 2.0)))
            (if east
              (progn
                (if (> nrow 0)
                  (progn (cg:add-wall (list xa current) (list leftAxis current) tWall height)
                    (cg:add-wall (list rightAxis current) (list xb current) tWall height)))
                (setq side 0)
                (foreach item (list west east)
                  (setq roomId (strcat "R" (itoa (1+ (length rooms)))))
                  (if (= side 0)
                    (setq box (list (+ x0 tExt) clearY0 (- ca tWall) clearY1)
                      wallId (cg:add-wall (list leftAxis current) (list leftAxis nextY) tWall height))
                    (setq box (list (+ cb tWall) clearY0 (- x1 tExt) clearY1)
                      wallId (cg:add-wall (list rightAxis current) (list rightAxis nextY) tWall height)))
                  (setq room (list (cons "id" roomId) (cons "name" (cg:get "name" item))
                    (cons "kind" (cg:get "kind" item)) (cons "bounds" box)
                    (cons "net_area_m2" (/ (* (- (nth 2 box) (nth 0 box)) (- (nth 3 box) (nth 1 box))) 1000000.0))))
                  (setq rooms (append rooms (list room)))
                  (cg:add-opening wallId "door" (list (if (= side 0) leftAxis rightAxis) (+ clearY0 650)) 800 2100 0 roomId)
                  (setq windowW (if (= (cg:get "kind" item) "bathroom") 600 1200))
                  (cg:add-opening (if (= side 0) exteriorLeft exteriorRight) "window"
                    (list (if (= side 0) xa xb) (/ (+ clearY0 clearY1) 2.0))
                    windowW (if (= windowW 600) 600 1000) (if (= windowW 600) 1600 1100) roomId)
                  (if (= (cg:get "furniture" params) 1) (cg:furnish room))
                  (setq side (1+ side))))
              (progn
                (setq corridorEnd (- current (/ tWall 2.0)) roomId (strcat "R" (itoa (1+ (length rooms)))))
                (setq wallId (cg:add-wall (list xa current) (list xb current) tWall height))
                (cg:add-opening wallId "door" (list (/ (+ ca cb) 2.0) current) 900 2100 0 roomId)
                (setq box (list (+ x0 tExt) clearY0 (- x1 tExt) clearY1))
                (setq room (list (cons "id" roomId) (cons "name" (cg:get "name" west))
                  (cons "kind" (cg:get "kind" west)) (cons "bounds" box)
                  (cons "net_area_m2" (/ (* (- (nth 2 box) (nth 0 box)) (- (nth 3 box) (nth 1 box))) 1000000.0))))
                (setq rooms (append rooms (list room)))
                (cg:add-opening exteriorBack "window" (list (/ (+ x0 x1) 2.0) (- yEnd (/ tExt 2.0))) 1200 1000 1100 roomId)
                (if (= (cg:get "furniture" params) 1) (cg:furnish room))))
            (setq current nextY nrow (1+ nrow)))
          (setq corridorRoom (list (cons "id" "CIRC") (cons "name" "Circulacao") (cons "kind" "corridor")
            (cons "bounds" (list ca (+ y0 tExt) cb corridorEnd))
            (cons "net_area_m2" (/ (* cw (- corridorEnd (+ y0 tExt))) 1000000.0))))
          (setq rooms (append rooms (list corridorRoom)) totalArea (/ (* (- x1 x0) (- yEnd y0)) 1000000.0))
          (list (cons "schema_version" "1.0") (cons "project_id" (cg:opt "project_id" params "CG-DEMO"))
            (cons "units" "mm") (cons "origin" (list ox oy 0.0)) (cons "algorithm_version" "corridor-0.1")
            (cons "seed" (cg:get "seed" params)) (cons "site_mode" "hypothetical_flat")
            (cons "site_bounds" (list ox oy (+ ox (cg:get "lot_width" params)) (+ oy (cg:get "lot_depth" params))))
            (cons "house_bounds" (list x0 y0 x1 yEnd)) (cons "gross_area_m2" totalArea)
            (cons "wall_internal" tWall) (cons "wall_external" tExt)
            (cons "walls" *cg-walls*) (cons "openings" *cg-openings*) (cons "rooms" rooms)
            (cons "furniture" *cg-furniture*)
            (cons "slab" (list (cons "bounds" (list x0 y0 x1 yEnd)) (cons "thickness" 150)))
            (cons "validations" (list
              (list (cons "rule_id" "PROGRAM") (cons "status" "pass") (cons "message" "Quantidades geradas conforme entrada; circulacao acrescentada."))
              (list (cons "rule_id" "BH") (cons "status" "not_evaluated") (cons "message" "Lote hipotetico; faixas de ensaio nao sao parametros municipais."))
              (list (cons "rule_id" "COMFORT") (cons "status" "not_evaluated") (cons "message" "Conforto, acessibilidade e operacao de mobiliario requerem verificacao."))))))))))
(princ)

;;; CASA BH 0.4. Articulated architectural organizations, millimetres.
;;; Geometric design targets only: no legal or thermal compliance implied.
(defun cl:area (b) (/ (* (- (nth 2 b) (nth 0 b)) (- (nth 3 b) (nth 1 b))) 1000000.0))
(defun cl:spec (kind name depth) (list (cons "kind" kind) (cons "name" name) (cons "depth" depth)))
(defun cl:room (spec axes / id b)
  (setq id (strcat "R" (itoa (1+ (length *cl-rooms*)))))
  (setq b (list (+ (nth 0 axes) (/ (if (equal (nth 0 axes) *cl-xa* 0.01) *cl-te* *cl-ti*) 2.0))
    (+ (nth 1 axes) (/ (if (equal (nth 1 axes) *cl-ya* 0.01) *cl-te* *cl-ti*) 2.0))
    (- (nth 2 axes) (/ (if (equal (nth 2 axes) *cl-xb* 0.01) *cl-te* *cl-ti*) 2.0))
    (- (nth 3 axes) (/ (if (equal (nth 3 axes) *cl-yb* 0.01) *cl-te* *cl-ti*) 2.0))))
  (setq *cl-rooms* (append *cl-rooms* (list (list (cons "id" id) (cons "kind" (cg:get "kind" spec))
    (cons "name" (cg:get "name" spec)) (cons "axes" axes) (cons "bounds" b) (cons "net_area_m2" (cl:area b)))))) id)
(defun cl:zone (kind name box room)
  (setq *cl-zones* (append *cl-zones* (list (list (cons "id" (strcat "Z" (itoa (1+ (length *cl-zones*)))))
    (cons "room_id" room) (cons "kind" kind) (cons "name" name) (cons "bounds" box) (cons "net_area_m2" (cl:area box)))))))
(defun cl:split (items / a b it sa sb)
  (setq sa 0.0 sb 0.0)
  (foreach it items (if (<= sa sb) (setq a (append a (list it)) sa (+ sa (cg:get "depth" it)))
    (setq b (append b (list it)) sb (+ sb (cg:get "depth" it)))))
  (list a b))
(defun cl:sumdepth (items / total it)
  (setq total 0.0) (foreach it items (setq total (+ total (cg:get "depth" it) *cl-ti*))) total)
(defun cl:depth-insert (item items)
  (cond ((not items) (list item))
    ((> (cg:get "depth" item) (cg:get "depth" (car items))) (cons item items))
    (T (cons (car items) (cl:depth-insert item (cdr items))))))
(defun cl:depth-sort (items / sorted item)
  (foreach item items (setq sorted (cl:depth-insert item sorted))) sorted)
(defun cl:section-depth (items lateral / parts)
  (setq parts (cl:split items)) (max (cl:sumdepth (car parts)) (cl:sumdepth (cadr parts))))
(defun cl:strip (items xlo xhi ya yb / cursor total extra spec dep largest)
  (setq cursor ya total (cl:sumdepth items) extra (- (- yb ya) total) largest (car items))
  (foreach spec items (if (> (cg:get "depth" spec) (cg:get "depth" largest)) (setq largest spec)))
  (foreach spec items
    (setq dep (+ (cg:get "depth" spec) *cl-ti* (if (equal spec largest) extra 0)))
    (cl:room spec (list xlo cursor xhi (+ cursor dep))) (setq cursor (+ cursor dep))))
(defun cl:section (items ya yb lateral / ca cb parts split)
  (progn
      (setq split (if lateral (+ 0.405 (* 0.025 (cg:rand))) (+ 0.46 (* 0.08 (cg:rand))))
        ca (+ *cl-xa* (* split (- (- *cl-xb* *cl-xa*) *cl-cw* *cl-ti*))) cb (+ ca *cl-cw* *cl-ti*)
        parts (cl:split items))
      (cl:strip (car parts) *cl-xa* ca ya yb) (cl:strip (cadr parts) cb *cl-xb* ya yb))
  (cl:room (cl:spec "corridor" "Circulacao" 0) (list ca ya cb yb)))
(defun cl:social (ya yb integration dining / room a b usable wl wd wk cursor specs spec rid axes bounds)
  (setq a (+ *cl-xa* (/ *cl-te* 2.0)) b (- *cl-xb* (/ *cl-te* 2.0)) usable (- b a)
    wl (if (= dining 1) 3000.0 (* usable 0.60)) wd (if (= dining 1) 2700.0 0.0)
    wk (- usable wl wd (cond ((= integration 3) (* (if (= dining 1) 2 1) *cl-ti*)) ((= integration 2) *cl-ti*) (T 0.0))))
  (setq specs (list (list "living" "Sala" wl)))
  (if (= dining 1) (setq specs (append specs (list (list "dining" "Jantar" wd)))))
  (setq specs (append specs (list (list "kitchen" "Cozinha" wk))))
  (cond
    ((= integration 1)
      (setq rid (cl:room (cl:spec "social" "Convivencia integrada" 0) (list *cl-xa* ya *cl-xb* yb)) cursor a)
      (foreach spec specs
        (cl:zone (car spec) (cadr spec) (list cursor (+ ya (/ (if (equal ya *cl-ya* 0.01) *cl-te* *cl-ti*) 2.0))
          (+ cursor (nth 2 spec)) (- yb (/ (if (equal yb *cl-yb* 0.01) *cl-te* *cl-ti*) 2.0))) rid)
        (setq cursor (+ cursor (nth 2 spec)))))
    ((= integration 2)
      (setq cursor (+ a wl wd (/ *cl-ti* 2.0)) rid (cl:room (cl:spec "social" (if (= dining 1) "Sala e jantar" "Sala") 0) (list *cl-xa* ya cursor yb)))
      (setq bounds (cg:get "bounds" (last *cl-rooms*)))
      (cl:zone "living" "Sala" (list a (nth 1 bounds) (+ a wl) (nth 3 bounds)) rid)
      (if (= dining 1) (cl:zone "dining" "Jantar" (list (+ a wl) (nth 1 bounds) (+ a wl wd) (nth 3 bounds)) rid))
      (cl:room (cl:spec "kitchen" "Cozinha" 0) (list cursor ya *cl-xb* yb)))
    (T
      (setq cursor *cl-xa*)
      (foreach spec specs
        (setq b (if (= (car spec) "kitchen") *cl-xb* (+ cursor (nth 2 spec) (if (equal cursor *cl-xa* 0.01) (/ (+ *cl-te* *cl-ti*) 2.0) *cl-ti*))))
        (cl:room (cl:spec (car spec) (cadr spec) 0) (list cursor ya b yb)) (setq cursor b)))))
(defun cl:recess-size (room / bounds)
  (setq bounds (cg:get "bounds" room))
  (min (if (member (cg:get "kind" room) '("bathroom" "laundry")) 1400 800)
    (- (nth 2 bounds) (car bounds) (if (member (cg:get "kind" room) '("bathroom" "laundry")) 2400 3300))))
(defun cl:articulate (frontside / room candidate axes bounds shift cut x y best leftside)
  ;; Choose the corner that offers the largest functional recess, including service rooms.
  (setq best -1)
  (foreach room *cl-rooms*
    (setq axes (cg:get "axes" room))
    (if (and (or (equal (car axes) *cl-xa* 0.01) (equal (nth 2 axes) *cl-xb* 0.01))
        (equal (if frontside (cadr axes) (nth 3 axes)) (if frontside *cl-ya* *cl-yb*) 0.01)
        (not (cl:social-p (cg:get "kind" room))) (> (cl:recess-size room) best))
      (setq candidate room best (cl:recess-size room))))
  (if (and candidate (> best 100))
    (progn
      (setq axes (cg:get "axes" candidate) bounds (cg:get "bounds" candidate) shift (* best (cg:opt "_recess_scale" params 1.0)) leftside (equal (car axes) *cl-xa* 0.01)
        axes (if leftside (cons (+ (car axes) shift) (cdr axes)) (list (car axes) (cadr axes) (- (nth 2 axes) shift) (nth 3 axes)))
        bounds (if leftside (cons (+ (car bounds) shift) (cdr bounds)) (list (car bounds) (cadr bounds) (- (nth 2 bounds) shift) (nth 3 bounds)))
        *cl-rooms* (subst (subst (cons "net_area_m2" (cl:area bounds)) (assoc "net_area_m2" candidate)
          (subst (cons "bounds" bounds) (assoc "bounds" candidate)
            (subst (cons "axes" axes) (assoc "axes" candidate) candidate))) candidate *cl-rooms*)
        x (if leftside (+ x0 shift) (- x1 shift))
        y (+ (if frontside (nth 3 axes) (cadr axes)) (if frontside (- (/ *cl-te* 2.0)) (/ *cl-te* 2.0))))
      (setq *cl-footprint*
        (if leftside
          (if frontside
            (list (list x y0) (list x1 y0) (list x1 ye) (list x0 ye) (list x0 y) (list x y))
            (list (list x0 y0) (list x1 y0) (list x1 ye) (list x ye) (list x y) (list x0 y)))
          (if frontside
            (list (list x0 y0) (list x y0) (list x y) (list x1 y) (list x1 ye) (list x0 ye))
            (list (list x0 y0) (list x1 y0) (list x1 y) (list x y) (list x ye) (list x0 ye))))))))
(defun cl:polygon-area (points / total a b seq)
  (setq total 0.0 seq (append points (list (car points))))
  (while (cdr seq) (setq a (car seq) b (cadr seq) total (+ total (- (* (car a) (cadr b)) (* (car b) (cadr a)))) seq (cdr seq)))
  (/ (abs total) 2000000.0))
(defun cl:edges (room / b id)
  (setq b (cg:get "axes" room) id (cg:get "id" room))
  (list (list "H" (nth 1 b) (nth 0 b) (nth 2 b) id) (list "H" (nth 3 b) (nth 0 b) (nth 2 b) id)
    (list "V" (nth 0 b) (nth 1 b) (nth 3 b) id) (list "V" (nth 2 b) (nth 1 b) (nth 3 b) id)))
(defun cl:unique-sort (vals / out val)
  (foreach val (vl-sort vals '<) (if (or (not out) (not (equal val (car out) 0.01))) (setq out (cons val out)))) (reverse out))
(defun cl:build-walls (/ edges room edge other cuts v starts end mid owners a b thick id wall)
  (foreach room *cl-rooms* (setq edges (append edges (cl:edges room))))
  (foreach edge edges
    (setq cuts (list (nth 2 edge) (nth 3 edge)))
    (foreach other edges
      (if (and (= (car edge) (car other)) (equal (cadr edge) (cadr other) 0.01))
        (foreach v (list (nth 2 other) (nth 3 other)) (if (and (> v (nth 2 edge)) (< v (nth 3 edge))) (setq cuts (cons v cuts))))))
    (setq cuts (cl:unique-sort cuts))
    (while (cdr cuts)
      (setq starts (car cuts) end (cadr cuts) mid (/ (+ starts end) 2.0) owners nil)
      (foreach other edges
        (if (and (= (car edge) (car other)) (equal (cadr edge) (cadr other) 0.01) (> mid (nth 2 other)) (< mid (nth 3 other)))
          (setq owners (cons (nth 4 other) owners))))
      (setq *cg-wall-role* (if (= (length owners) 1) "external" "internal") thick (if (= *cg-wall-role* "external") *cl-te* *cl-ti*)
        a (if (= (car edge) "H") (list starts (cadr edge)) (list (cadr edge) starts))
        b (if (= (car edge) "H") (list end (cadr edge)) (list (cadr edge) end))
        id (cg:add-wall a b thick *cl-height*))
      (setq wall (car (vl-remove-if-not '(lambda (w) (= (cg:get "id" w) id)) *cg-walls*)))
      (if (not (assoc "room_ids" wall)) (setq *cg-walls* (subst (append wall (list (cons "room_ids" owners))) wall *cg-walls*)))
      (setq cuts (cdr cuts)))))
(defun cl:remeasure (/ room axes b wall a c side zone host zb)
  (foreach room *cl-rooms*
    (setq axes (cg:get "axes" room) b (list (+ (car axes) (/ *cl-ti* 2.0)) (+ (cadr axes) (/ *cl-ti* 2.0)) (- (nth 2 axes) (/ *cl-ti* 2.0)) (- (nth 3 axes) (/ *cl-ti* 2.0))))
    (foreach wall *cg-walls*
      (if (and (= (length (cg:get "room_ids" wall)) 1) (member (cg:get "id" room) (cg:get "room_ids" wall)))
        (progn (setq a (cg:get "start" wall) c (cg:get "end" wall))
          (cond
            ((and (equal (car a) (car c) 0.01) (equal (car a) (car axes) 0.01)) (setq b (list (+ (car axes) (/ *cl-te* 2.0)) (cadr b) (nth 2 b) (nth 3 b))))
            ((equal (car a) (car c) 0.01) (setq b (list (car b) (cadr b) (- (nth 2 axes) (/ *cl-te* 2.0)) (nth 3 b))))
            ((equal (cadr a) (cadr axes) 0.01) (setq b (list (car b) (+ (cadr axes) (/ *cl-te* 2.0)) (nth 2 b) (nth 3 b))))
            (T (setq b (list (car b) (cadr b) (nth 2 b) (- (nth 3 axes) (/ *cl-te* 2.0)))))))))
    (setq *cl-rooms* (subst (subst (cons "net_area_m2" (cl:area b)) (assoc "net_area_m2" room) (subst (cons "bounds" b) (assoc "bounds" room) room)) room *cl-rooms*)))
  (foreach zone *cl-zones*
    (setq host (cl:room-by-id (cg:get "room_id" zone)) b (cg:get "bounds" host) zb (cg:get "bounds" zone)
      zb (list (max (car b) (car zb)) (max (cadr b) (cadr zb)) (min (nth 2 b) (nth 2 zb)) (min (nth 3 b) (nth 3 zb))))
    (setq *cl-zones* (subst (subst (cons "net_area_m2" (cl:area zb)) (assoc "net_area_m2" zone) (subst (cons "bounds" zb) (assoc "bounds" zone) zone)) zone *cl-zones*))))
(defun cl:room-by-id (id) (car (vl-remove-if-not '(lambda (r) (= (cg:get "id" r) id)) *cl-rooms*)))
(defun cl:social-p (kind) (member kind '("social" "living" "dining" "kitchen")))
(defun cl:length (wall) (distance (cg:get "start" wall) (cg:get "end" wall)))
(defun cl:door (wall room other width style / a b center opening)
  (setq a (cg:get "start" wall) b (cg:get "end" wall) center (mapcar '(lambda (u v) (/ (+ u v) 2.0)) a b))
  (if (and other (cl:social-p (cg:get "kind" (cl:room-by-id room))) (cl:social-p (cg:get "kind" (cl:room-by-id other)))
      (equal (car a) (car b) 0.01)) (setq center (list (car a) (+ (cadr a) 700))))
  (cg:add-opening (cg:get "id" wall) "door" center width 2100 0 room)
  (setq opening (last *cg-openings*))
  (setq *cg-openings* (subst (append opening (list (cons "door_style" style) (cons "connected_room_id" (if other other "EXTERIOR")))) opening *cg-openings*)))
(defun cl:openings (/ wall owners r1 r2 k1 k2 room best candidate win a b width entry bestlen zone entrance opening entrancex)
  ;; Every private room opens to a corridor; social rooms connect to each other.
  (foreach wall *cg-walls*
    (setq owners (cg:get "room_ids" wall))
    (if (= (length owners) 2)
      (progn (setq r1 (cl:room-by-id (car owners)) r2 (cl:room-by-id (cadr owners)) k1 (cg:get "kind" r1) k2 (cg:get "kind" r2))
        (if (and (> (cl:length wall) 1050)
          (or (= k1 "corridor") (= k2 "corridor") (and (cl:social-p k1) (cl:social-p k2))))
          (cl:door wall (if (= k1 "corridor") (cg:get "id" r2) (cg:get "id" r1))
            (if (= k1 "corridor") (cg:get "id" r1) (cg:get "id" r2))
            (if (or (= k1 "corridor") (= k2 "corridor")) 900 1000)
            (if (and (cl:social-p k1) (cl:social-p k2) (= integration 3)) "sliding"
              (if (and (or (cl:social-p k1) (= k1 "corridor")) (or (cl:social-p k2) (= k2 "corridor"))) "passage" "hinged")))))))
  ;; Principal arrival always on the front, including a distribution hall/corridor.
  (setq entry nil bestlen -1)
  (foreach wall *cg-walls*
    (setq owners (cg:get "room_ids" wall))
    (if (and (= (length owners) 1) (or (cl:social-p (cg:get "kind" (cl:room-by-id (car owners)))) (= (cg:get "kind" (cl:room-by-id (car owners))) "corridor")) (> (cl:length wall) 1050)
        (equal (cadr (cg:get "start" wall)) *cl-ya* 0.01) (equal (cadr (cg:get "end" wall)) *cl-ya* 0.01))
      (progn
        (setq a (cg:get "start" wall) b (cg:get "end" wall)
          candidate (+ (cl:length wall) (if (and (equal (cadr a) *cl-ya* 0.01) (equal (cadr b) *cl-ya* 0.01)) 100000 0)))
        (if (> candidate bestlen) (setq bestlen candidate entry wall)))))
  (if entry (progn (cl:door entry (car (cg:get "room_ids" entry)) nil 1000 "hinged")
    (setq opening (last *cg-openings*))
    (foreach zone *cl-zones*
      (if (and (= (cg:get "room_id" zone) (cg:get "room_id" opening)) (= (cg:get "kind" zone) "living"))
        (progn (setq entrance (cg:get "bounds" zone) entrancex (/ (+ (car entrance) (nth 2 entrance)) 2.0))
          (setq *cg-openings* (subst (subst (cons "center" (list entrancex *cl-ya*)) (assoc "center" opening) opening) opening *cg-openings*)))))
    (setq *cl-main-entry* (cg:get "id" (last *cg-openings*)) *cl-entry-center* (cg:get "center" (last *cg-openings*)))))
  ;; Windows on each functional zone, unless the same external segment carries the entry.
  (foreach room *cl-rooms*
    (if (/= (cg:get "kind" room) "corridor")
      (progn (setq best nil bestlen 0)
        (foreach wall *cg-walls*
          (if (and (= (length (cg:get "room_ids" wall)) 1) (member (cg:get "id" room) (cg:get "room_ids" wall))
              (not (equal wall entry)) (> (cl:length wall) bestlen)) (setq best wall bestlen (cl:length wall))))
        (if best
          (progn (setq a (cg:get "start" best) b (cg:get "end" best) width (min (- bestlen 400) (if (= (cg:get "kind" room) "bathroom") 800 1600)))
            (if (> width 500) (cg:add-opening (cg:get "id" best) "window" (mapcar '(lambda (u v) (/ (+ u v) 2.0)) a b)
              width (if (= (cg:get "kind" room) "bathroom") 600 1200) (if (= (cg:get "kind" room) "bathroom") 1600 1000) (cg:get "id" room)))))))))
(defun cl:zone-windows (/ zone box wall a b owners lo hi mid vertical width center conflict opening)
  ;; More than one window is allowed on a host; functional social zones receive their own apertures.
  (foreach zone *cl-zones*
    (setq box (cg:get "bounds" zone))
    (foreach wall *cg-walls*
      (setq owners (cg:get "room_ids" wall))
      (if (and (= (length owners) 1) (member (cg:get "room_id" zone) owners))
        (progn
          (setq a (cg:get "start" wall) b (cg:get "end" wall) vertical (equal (car a) (car b) 0.01)
            lo (max (if vertical (cadr a) (car a)) (if vertical (cadr box) (car box)))
            hi (min (if vertical (cadr b) (car b)) (if vertical (nth 3 box) (nth 2 box))))
          (if (and (> (- hi lo) 1300)
              (if vertical (or (< (abs (- (car a) (car box))) 160) (< (abs (- (car a) (nth 2 box))) 160))
                (or (< (abs (- (cadr a) (cadr box))) 160) (< (abs (- (cadr a) (nth 3 box))) 160))))
            (progn
              (setq mid (/ (+ lo hi) 2.0) width (if (= (cg:get "kind" zone) "bathroom") 800 (min 1500 (- hi lo 400)))
                center (if vertical (list (car a) mid) (list mid (cadr a))) conflict nil)
              (foreach opening *cg-openings*
                (if (and (= (cg:get "wall_id" opening) (cg:get "id" wall))
                    (< (distance center (cg:get "center" opening)) (+ 150 (/ (+ width (cg:get "width" opening)) 2.0)))) (setq conflict T)))
              (if (not conflict) (cg:add-opening (cg:get "id" wall) "window" center width
                (if (= (cg:get "kind" zone) "bathroom") 600 1200) (if (= (cg:get "kind" zone) "bathroom") 1600 1000) (cg:get "room_id" zone))))))))))
(defun cl:reachable (/ reached changed opening a b room missing)
  (setq reached '("EXTERIOR") changed T)
  (while changed
    (setq changed nil)
    (foreach opening *cg-openings*
      (if (= (cg:get "kind" opening) "door")
        (progn (setq a (cg:get "room_id" opening) b (cg:get "connected_room_id" opening))
          (cond ((and (member a reached) (not (member b reached))) (setq reached (cons b reached) changed T))
            ((and (member b reached) (not (member a reached))) (setq reached (cons a reached) changed T)))))))
  (foreach room *cl-rooms* (if (not (member (cg:get "id" room) reached)) (setq missing T))) (not missing))
(defun cl:generate-candidate (params / err *cg-walls* *cg-openings* *cg-furniture* *cg-seed* *cg-wall-role*
    *cl-footprint* *cl-main-entry* *cl-entry-center* *cl-rooms* *cl-zones* *cl-ti* *cl-te* *cl-height* *cl-cw* *cl-xa* *cl-xb* *cl-ya* *cl-yb*
    specs spec idx program layout integration parking occupants north ox oy x0 x1 y0 ye front
    nfirst groupa groupb item da db socialdepth socialya socialyb total room model outdoor garagewidth rearspace checks circarea netarea winarea wincount gx gy pathstart pathcorner entrypath)
  (setq err (cg:validate-input params))
  (foreach spec '(("parking" 0 2 1) ("occupants" 1 6 4) ("layout" 0 3 0) ("integration" 0 3 0) ("terrace" 0 1 1))
    (setq item (cg:opt (car spec) params (nth 3 spec)))
    (if (or (not (numberp item)) (< item (cadr spec)) (> item (nth 2 spec)) (/= item (fix item))) (setq err (strcat "Campo invalido: " (car spec)))))
  (setq north (cg:opt "north" params 0))
  (if (or (not (numberp north)) (< north 0) (>= north 360)) (setq err "Norte deve estar entre 0 e 359.99 graus."))
  (if (and (not err) (or (> (cg:get "living" params) 1) (> (cg:get "kitchens" params) 1) (> (cg:get "dining" params) 1)))
    (setq err "Versao 0.3 aceita uma sala, uma cozinha e ate um jantar; multiplos setores sociais ainda nao implementados."))
  (if (and (not err) (> (cg:opt "occupants" params 4) (* 2 (cg:get "bedrooms" params)))) (setq err "Moradores excedem capacidade de duas pessoas por quarto."))
  (if err (list (cons "error" err))
    (progn
      (setq *cg-seed* (cg:get "seed" params) *cl-ti* (cg:wall-thickness "wall_internal" params) *cl-te* (cg:wall-thickness "wall_external" params)
        *cl-height* (cg:get "height" params) *cl-cw* (cg:get "corridor" params) parking (fix (cg:opt "parking" params 1))
        occupants (fix (cg:opt "occupants" params 4)) layout (fix (cg:opt "layout" params 0)) integration (fix (cg:opt "integration" params 0))
        ox (cg:opt "origin_x" params 0) oy (cg:opt "origin_y" params 0))
      ;; Advance the seed before categorical selection: nearby seeds must differ too.
      (repeat 4 (cg:rand))
      (if (= layout 0) (setq layout (1+ (fix (* 3 (cg:rand))))))
      (if (= integration 0) (setq integration (1+ (fix (* 3 (cg:rand))))))
      (foreach spec '(("bedrooms" "bedroom" "Quarto" 3400) ("bathrooms" "bathroom" "Banheiro" 2300)
          ("laundry" "laundry" "Lavanderia" 2200) ("office" "office" "Escritorio" 2900))
        (setq idx 1)
        (repeat (fix (cg:get (car spec) params))
          (setq program (append program (list (cl:spec (cadr spec) (strcat (nth 2 spec) " " (itoa idx))
            (+ (nth 3 spec) (* 100 (fix (* 5 (cg:rand))))))))) (setq idx (1+ idx))))
      (setq program (cg:shuffle program))
      ;; Similar-depth front rooms avoid enlarging a single bathroom to match a bedroom.
      (if (= layout 3) (setq program (cl:depth-sort program)))
      (if (and (= layout 3) (< (length program) 4)) (setq err "Organizacao central exige ao menos quatro ambientes privados/servico; selecione frente ou fundo."))
      (setq x0 (+ ox (cg:get "side" params)) x1 (+ x0 (cg:get "house_width" params))
        front (max (cg:get "front" params) (if (> parking 0) 6500 0)) y0 (+ oy front)
        *cl-xa* (+ x0 (/ *cl-te* 2.0)) *cl-xb* (- x1 (/ *cl-te* 2.0)) *cl-ya* (+ y0 (/ *cl-te* 2.0))
        socialdepth (+ 3600 (* 100 (fix (* 6 (cg:rand)))) *cl-ti*))
      (if (= layout 3)
        (progn (setq nfirst (fix (/ (length program) 2)) idx 0)
          (foreach item program (if (< idx nfirst) (setq groupa (append groupa (list item))) (setq groupb (append groupb (list item)))) (setq idx (1+ idx)))
          (setq da (cl:section-depth groupa nil) db (cl:section-depth groupb nil)))
        (if (= layout 2) (setq da (cl:section-depth program nil) db 0) (setq da 0 db (cl:section-depth program nil))))
      (setq total (+ da socialdepth db) *cl-yb* (+ *cl-ya* total) ye (+ *cl-yb* (/ *cl-te* 2.0))
        socialya (+ *cl-ya* da) socialyb (+ socialya socialdepth))
      (if (> ye (- (+ oy (cg:get "lot_depth" params)) (cg:get "rear" params)))
        (setq err (strcat "Esta organizacao precisa de " (rtos (/ (+ total *cl-te*) 1000.0) 2 2) "m de profundidade construida. Aumente lote/reduza programa ou selecione outra organizacao.")))
      (if (< (- (cg:get "house_width" params) (* 2 *cl-te*) (if (= integration 3) (* (if (= (cg:get "dining" params) 1) 2 1) *cl-ti*) (if (= integration 2) *cl-ti* 0)))
          (if (= (cg:get "dining" params) 1) 8300 5600)) (setq err "Largura insuficiente para sala/cozinha/jantar e mobiliario neste perfil. Aumente largura ou altere integracao."))
      (if (and (> parking 0) (< (cg:get "lot_width" params) (+ (* parking 2600) 1200))) (setq err "Garagem e percurso pedestre nao cabem na largura do lote."))
      (if err (list (cons "error" err))
        (progn
          (if (= layout 3) (cl:section groupa *cl-ya* socialya nil))
          (if (= layout 2) (cl:section program *cl-ya* socialya nil))
          (cl:social socialya socialyb integration (fix (cg:get "dining" params)))
          (if (/= layout 2) (cl:section (if (= layout 3) groupb program) socialyb *cl-yb* nil))
          (setq *cl-footprint* (list (list x0 y0) (list x1 y0) (list x1 ye) (list x0 ye)))
          (cl:articulate (= layout 2))
          (cl:build-walls) (cl:remeasure)
          (foreach room *cl-rooms*
            (if (not (member (cg:get "kind" room) '("social" "corridor")))
              (cl:zone (cg:get "kind" room) (cg:get "name" room) (cg:get "bounds" room) (cg:get "id" room))))
          (cl:openings) (cl:zone-windows)
          (if (> parking 0)
            (progn
              (setq garagewidth (* parking 2600) gx (max ox (min (- (+ ox (cg:get "lot_width" params)) garagewidth 1200) (- (car *cl-entry-center*) garagewidth 600)))
                gy (- y0 6500) pathstart (list (+ gx garagewidth 600) (+ gy 4300))
                pathcorner (list (car *cl-entry-center*) (- y0 600))
                entrypath (list (cons "points" (list pathstart (list (car pathstart) (cadr pathcorner)) pathcorner *cl-entry-center*))
                  (cons "width" 1200) (cons "length" (+ (- (cadr pathcorner) (cadr pathstart)) (abs (- (car pathcorner) (car pathstart))) (- (cadr *cl-entry-center*) (cadr pathcorner))))))
            (setq outdoor (list (list (cons "id" "EXT-GARAGE") (cons "kind" "garage") (cons "name" "Garagem descoberta")
              (cons "spaces" parking) (cons "bounds" (list gx gy (+ gx garagewidth) (+ gy 5000))))))))
          (setq rearspace (- (+ oy (cg:get "lot_depth" params)) ye))
          (if (and (= (cg:opt "terrace" params 1) 1) (>= rearspace 1800))
            (setq outdoor (append outdoor (list (list (cons "id" "EXT-TERRACE") (cons "kind" "terrace") (cons "name" "Convivencia descoberta")
              (cons "bounds" (list x0 ye (min x1 (+ x0 4000)) (+ ye (min 2500 rearspace)))))))))
          ;; Rear access through the corridor when possible, preserving private rooms.
          (foreach item *cg-walls*
            (if (and (= (length (cg:get "room_ids" item)) 1)
                (= (cg:get "kind" (cl:room-by-id (car (cg:get "room_ids" item)))) "corridor")
                (equal (cadr (cg:get "start" item)) *cl-yb* 0.01) (equal (cadr (cg:get "end" item)) *cl-yb* 0.01))
              (cl:door item (car (cg:get "room_ids" item)) nil 900 "hinged")))
          (setq checks (list
            (list (cons "rule_id" "PROGRAM") (cons "status" "pass") (cons "message" "Quantidades funcionais preservadas em zones; integracao altera numero de recintos."))
            (list (cons "rule_id" "ACCESS_GRAPH") (cons "status" (if (cl:reachable) "pass" "fail")) (cons "message" "Grafo de portas conecta todos os recintos ao exterior; nao equivale a rota acessivel."))
            (list (cons "rule_id" "MAIN_ARRIVAL") (cons "status" (if (and *cl-main-entry* (or (= parking 0) (<= (cg:get "length" entrypath) 6000))) "pass" "fail")) (cons "message" "Entrada frontal conectada a garagem por faixa pedestre 1.20m; distancia alvo ate 6m e criterio de projeto, nao norma."))
            (list (cons "rule_id" "BH") (cons "status" "not_evaluated") (cons "message" "Faixas hipoteticas; garagem e area externa dependem das regras reais do lote."))
            (list (cons "rule_id" "DAYLIGHT_THERMAL") (cons "status" "not_evaluated") (cons "message" "Aberturas externas previstas; norte informativo. Insolacao, ventilacao, materiais e entorno nao simulados."))))
          (setq circarea 0.0 netarea 0.0 winarea 0.0 wincount 0)
          (foreach room *cl-rooms* (setq netarea (+ netarea (cg:get "net_area_m2" room)))
            (if (= (cg:get "kind" room) "corridor") (setq circarea (+ circarea (cg:get "net_area_m2" room)))))
          (foreach item *cg-openings* (if (= (cg:get "kind" item) "window")
            (setq wincount (1+ wincount) winarea (+ winarea (/ (* (cg:get "width" item) (cg:get "height" item)) 1000000.0)))))
          (setq model (list (cons "schema_version" "1.0") (cons "project_id" (cg:opt "project_id" params "CG-DEMO")) (cons "units" "mm")
            (cons "origin" (list ox oy 0.0)) (cons "algorithm_version" "architectural-0.4") (cons "seed" (cg:get "seed" params))
            (cons "front_effective" front) (cons "layout" layout) (cons "integration" integration) (cons "north" north) (cons "north_degrees" north) (cons "occupants" occupants)
            (cons "layout_name" (nth (1- layout) '("Social na frente" "Convivencia no fundo" "Convivencia central")))
            (cons "integration_name" (nth (1- integration) '("Integrada" "Semi-integrada" "Separada")))
            (cons "circulation_area_m2" circarea) (cons "circulation_fraction" (/ circarea netarea))
            (cons "windows_count" wincount) (cons "window_area_m2" winarea)
            (cons "site_mode" "hypothetical_flat") (cons "site_bounds" (list ox oy (+ ox (cg:get "lot_width" params)) (+ oy (cg:get "lot_depth" params))))
            (cons "house_bounds" (list x0 y0 x1 ye)) (cons "footprint" *cl-footprint*) (cons "main_entry_id" *cl-main-entry*) (cons "entry_path" entrypath)
            (cons "gross_area_m2" (cl:polygon-area *cl-footprint*))
            (cons "wall_internal" *cl-ti*) (cons "wall_external" *cl-te*) (cons "walls" *cg-walls*) (cons "openings" *cg-openings*)
            (cons "rooms" *cl-rooms*) (cons "zones" *cl-zones*) (cons "outdoor" outdoor) (cons "furniture" nil)
            (cons "slab" (list (cons "bounds" (list x0 y0 x1 ye)) (cons "outline" *cl-footprint*) (cons "thickness" 150))) (cons "validations" checks)))
          (if (not (cl:reachable)) (list (cons "error" "Candidato rejeitado: recinto sem caminho de portas ate exterior."))
            (cg:furnish-model (cg:with-roof model) params)))))))
(princ)




;;; Bounded deterministic backtracking: preserve the program and furniture checks.
(defun cg:generate (params / model factors factor attempts result)
 (setq factors '(1.0 0.75 0.5) model nil attempts 0)
 (while factors
  (setq factor (car factors) factors (cdr factors) attempts (1+ attempts)
   model (cl:generate-candidate (cons (cons "_recess_scale" factor) params)))
  (if (not (cg:get "error" model))
   (progn (setq model (append model (list (cons "recess_scale" factor) (cons "geometry_attempts" attempts)))) (setq factors nil))
   (if (not (wcmatch (cg:get "error" model) "Conjunto*")) (setq factors nil))))
 model)
(princ)

;;; CASA BH furniture 0.3. Prototype dimensions in mm; no regulatory claim.
(defun cf:rect (x y w h) (list x y (+ x w) (+ y h)))
(defun cf:hit (a b) (and (< (car a) (- (nth 2 b) 0.1)) (> (nth 2 a) (+ (car b) 0.1)) (< (cadr a) (- (nth 3 b) 0.1)) (> (nth 3 a) (+ (cadr b) 0.1))))
(defun cf:inside (a b) (and (>= (car a) (- (car b) 0.1)) (>= (cadr a) (- (cadr b) 0.1)) (<= (nth 2 a) (+ (nth 2 b) 0.1)) (<= (nth 3 a) (+ (nth 3 b) 0.1))))
(defun cf:item (kind box height use) (list (cons "kind" kind) (cons "bounds" box) (cons "height" height) (cons "use_bounds" (if use use box))))
(defun cf:template (kind w h double / out bx by bw seats tl cols dx)
  (setq out nil)
  (cond
    ((= kind "bedroom")
      (setq bw (if double 1380.0 880.0) bx (/ (- w bw) 2.0) by (- h 1980))
      (setq out (list
        (cf:item (if double "bed_double" "bed_single") (cf:rect bx by bw 1880) 550 (list (- bx 500) (- by 500) (+ bx bw 500) (- h 100)))
        (cf:item "wardrobe" (cf:rect 100 100 1500 600) 2200 (cf:rect 100 100 1500 1100))
        (cf:item "nightstand" (cf:rect (- bx 450) (- h 550) 400 450) 550 nil))))
    ((= kind "living")
      (setq seats (if *cf-occupants* *cf-occupants* 4))
      (if (<= seats 3)
        (setq out (list
          (cf:item "sofa" (cf:rect (/ (- w 2200) 2.0) (- h 1000) 2200 900) 850 (cf:rect (/ (- w 2200) 2.0) (- h 1600) 2200 1500))
          (cf:item "tv_rack" (cf:rect (/ (- w 1500) 2.0) 100 1500 350) 550 (cf:rect (/ (- w 1500) 2.0) 100 1500 950))))
        (setq out (list
          (cf:item "sofa" (cf:rect (/ (- w 2200) 2.0) (- h 1000) 2200 900) 850 (cf:rect (/ (- w 2200) 2.0) (- h 1600) 2200 1500))
          (cf:item "sofa" (cf:rect (/ (- w 2200) 2.0) 100 2200 900) 850 (cf:rect (/ (- w 2200) 2.0) 100 2200 1500))
          (cf:item "tv_rack" (cf:rect 50 (/ (- h 1000) 2.0) 300 1000) 550 (cf:rect 50 (/ (- h 1000) 2.0) 900 1000)))))
      (if (= seats 4)
        (setq out (list
          (cf:item "sofa" (cf:rect (/ (- w 2200) 2.0) (- h 1000) 2200 900) 850 (cf:rect (/ (- w 2200) 2.0) (- h 1600) 2200 1500))
          (cf:item "armchair" (cf:rect 100 100 750 750) 850 (cf:rect 100 100 750 1350))
          (cf:item "tv_rack" (cf:rect (- w 350) 1400 300 1000) 550 (cf:rect (- w 950) 1400 900 1000)))))
      (if (and (>= seats 5) *cf-variant* (= *cf-variant* 1))
        (progn
          (setq out (list
            (cf:item "sofa" (cf:rect (/ (- w 2200) 2.0) (- h 1000) 2200 900) 850 (cf:rect (/ (- w 2200) 2.0) (- h 1600) 2200 1500))
            (cf:item "loveseat" (cf:rect 100 100 800 1600) 850 (cf:rect 100 100 1400 1600))
            (cf:item "tv_rack" (cf:rect (- w 350) 1400 300 1000) 550 (cf:rect (- w 950) 1400 900 1000))))
          (if (= seats 6) (setq out (append out (list
            (cf:item "armchair" (cf:rect (- w 850) 100 750 750) 850 (cf:rect (- w 850) 100 750 1250))))))))      (if (> seats 6) (setq out nil)))
    ((= kind "dining")
      (setq seats (if *cf-occupants* *cf-occupants* 4) cols (cond ((<= seats 4) 2) ((<= seats 6) 3) (T 4)) tl (cond ((= cols 2) 1400) ((= cols 3) 1800) (T 2300)) bx (/ (- w tl) 2.0) by (/ (- h 800) 2.0))
      (setq out (list (cf:item "dining_table" (cf:rect bx by tl 800) 750 nil)) dx 100)
      (repeat cols
        (setq out (append out (list
          (cf:item "dining_chair" (cf:rect (+ bx dx) (- by 450) 450 400) 850 (cf:rect (+ bx dx) (- by 850) 450 800))
          (cf:item "dining_chair" (cf:rect (+ bx dx) (+ by 850) 450 400) 850 (cf:rect (+ bx dx) (+ by 850) 450 800)))))
        (setq dx (+ dx 550))))
    ((= kind "kitchen")
      (setq out (list
        (cf:item "fridge" (cf:rect 100 (- h 850) 700 750) 1800 (cf:rect 100 (- h 1600) 700 1500))
        (cf:item "sink" (cf:rect 850 (- h 700) 600 600) 900 (cf:rect 850 (- h 1500) 600 1400))
        (cf:item "counter" (cf:rect 1450 (- h 700) 400 600) 900 (cf:rect 1450 (- h 1500) 400 1400))
        (cf:item "stove" (cf:rect 1900 (- h 700) 600 600) 900 (cf:rect 1900 (- h 1500) 600 1400)))))
    ((= kind "bathroom")
      (setq out (list
        (cf:item "shower" (cf:rect 100 (- h 1000) 900 900) 100 (cf:rect 100 (- h 1500) 900 1400))
        (cf:item "toilet" (cf:rect 1100 (- h 850) 650 750) 700 (cf:rect 1100 (- h 1450) 650 1350))
        (cf:item "basin" (cf:rect (- w 650) 100 550 450) 850 (cf:rect (- w 1250) 100 1150 450)))))
    ((= kind "laundry")
      (setq out (list
        (cf:item "washer" (cf:rect 100 (- h 800) 650 700) 900 (cf:rect 100 (- h 1500) 650 1400))
        (cf:item "laundry_sink" (cf:rect 850 (- h 700) 600 600) 900 (cf:rect 850 (- h 1500) 600 1400)))))
    ((= kind "office")
      (setq bx (/ (- w 1200) 2.0))
      (setq out (list
        (cf:item "desk" (cf:rect bx (- h 700) 1200 600) 750 nil)
        (cf:item "office_chair" (cf:rect (+ bx 350) (- h 1300) 500 500) 950 (cf:rect (+ bx 250) (- h 1700) 700 900)))))
    ((= kind "garage")
      (setq cols (if *cf-garage-spaces* *cf-garage-spaces* 1) dx 0 bw (/ w cols))
      (repeat cols
        (setq out (append out (list (cf:item "car" (cf:rect (+ dx (/ (- bw 1800) 2.0)) (/ (- h 4400) 2.0) 1800 4400) 1500 (cf:rect (+ dx (/ (- bw 2600) 2.0)) (/ (- h 4800) 2.0) 2600 4800)))))
        (setq dx (+ dx bw))))    ((member kind '("veranda" "terrace"))
      (setq out (list (cf:item "bench" (cf:rect 100 (- h 550) 1500 450) 800 (cf:rect 100 (- h 1150) 1500 1050)))))
  ) out)
(defun cf:pt (p w h rot mirror / x y)
  (setq x (car p) y (cadr p))
  (if mirror (setq x (- w x)))
  (cond ((= rot 0) (list x y)) ((= rot 1) (list (- h y) x)) ((= rot 2) (list (- w x) (- h y))) (T (list y (- w x)))))
(defun cf:transform (b box w h rot mirror / a c)
  (setq a (cf:pt (list (car b) (cadr b)) w h rot mirror) c (cf:pt (list (nth 2 b) (nth 3 b)) w h rot mirror))
  (list (+ (car box) (min (car a) (car c))) (+ (cadr box) (min (cadr a) (cadr c))) (+ (car box) (max (car a) (car c))) (+ (cadr box) (max (cadr a) (cadr c)))))
(defun cf:doors (box model / out op c wd depth x y ds)
  (setq out nil)
  (foreach op (cg:get "openings" model)
    (if (= (cg:get "kind" op) "door")
      (progn
        (setq c (cg:get "center" op) wd (+ (/ (cg:get "width" op) 2.0) 50) x (car c) y (cadr c)
          ds (cg:opt "door_style" op "swing") depth (if (member ds '("passage" "sliding")) 450 (+ (cg:get "width" op) 100)))
        (cond
          ((and (<= (abs (- x (car box))) 350) (> y (cadr box)) (< y (nth 3 box))) (setq out (cons (list (car box) (- y wd) (+ (car box) depth) (+ y wd)) out)))
          ((and (<= (abs (- x (nth 2 box))) 350) (> y (cadr box)) (< y (nth 3 box))) (setq out (cons (list (- (nth 2 box) depth) (- y wd) (nth 2 box) (+ y wd)) out)))
          ((and (<= (abs (- y (cadr box))) 350) (> x (car box)) (< x (nth 2 box))) (setq out (cons (list (- x wd) (cadr box) (+ x wd) (+ (cadr box) depth)) out)))
          ((and (<= (abs (- y (nth 3 box))) 350) (> x (car box)) (< x (nth 2 box))) (setq out (cons (list (- x wd) (- (nth 3 box) depth) (+ x wd) (nth 3 box)) out))))))) out)
(defun cf:valid (items box doors / ok a b d)
  (setq ok T)
  (foreach a items
    (if (not (and (cf:inside (cg:get "bounds" a) box) (cf:inside (cg:get "use_bounds" a) box))) (setq ok nil))
    (foreach b items (if (and (not (eq a b)) (or (cf:hit (cg:get "bounds" a) (cg:get "bounds" b)) (and (not (and (member (cg:get "kind" a) '("bed_double" "bed_single")) (= (cg:get "kind" b) "nightstand"))) (cf:hit (cg:get "use_bounds" a) (cg:get "bounds" b))))) (setq ok nil)))
    (foreach d doors (if (cf:hit (cg:get "bounds" a) d) (setq ok nil)))) ok)
(defun cf:window-clear (items model / ok it op wall a b c half band candidate)
  (setq ok T)
  (foreach op (cg:get "openings" model)
    (if (= (cg:get "kind" op) "window")
      (progn
        (setq wall nil)
        (foreach candidate (cg:get "walls" model) (if (= (cg:get "id" candidate) (cg:get "wall_id" op)) (setq wall candidate)))
        (if wall
          (progn
            (setq a (cg:get "start" wall) b (cg:get "end" wall) c (cg:get "center" op) half (/ (cg:get "width" op) 2.0))
            (if (equal (car a) (car b) 0.1)
              (setq band (list (- (car c) (+ 200 (/ (cg:get "thickness" wall) 2.0))) (- (cadr c) half) (+ (car c) (+ 200 (/ (cg:get "thickness" wall) 2.0))) (+ (cadr c) half)))
              (setq band (list (- (car c) half) (- (cadr c) (+ 200 (/ (cg:get "thickness" wall) 2.0))) (+ (car c) half) (+ (cadr c) (+ 200 (/ (cg:get "thickness" wall) 2.0))))))
            (foreach it items
              (if (and (> (cg:get "height" it) (cg:opt "sill" op 900)) (cf:hit (cg:get "bounds" it) band)) (setq ok nil)))))))) ok)(defun cf:outline (b)
  (list (list (car b) (cadr b)) (list (nth 2 b) (cadr b)) (list (nth 2 b) (nth 3 b)) (list (car b) (nth 3 b)) (list (car b) (cadr b))))
;;; All symbol lines are WORLD coordinates; importers must not rotate them again.
(defun cf:symbol (it zonebox w h rot mir / b k x y xx yy bw bh out ln pts pt q)
  (setq b (cg:get "bounds" it) k (cg:get "kind" it) x (car b) y (cadr b) xx (nth 2 b) yy (nth 3 b) bw (- xx x) bh (- yy y) out nil)
  (cond
    ((member k '("bed_double" "bed_single"))
      (setq out (list (cf:outline (list (+ x 70) (- yy 420) (- xx 70) (- yy 70)))
        (list (list x (- yy 520)) (list xx (- yy 520)))))
      (if (= k "bed_double") (setq out (cons (list (list (/ (+ x xx) 2.0) (- yy 420)) (list (/ (+ x xx) 2.0) (- yy 70))) out))))
    ((member k '("sofa" "loveseat" "armchair" "bench"))
      (if (>= bw bh)
        (setq out (list (list (list (+ x 70) (if (> (/ (+ y yy) 2.0) (/ h 2.0)) (- yy 160) (+ y 160)))
          (list (- xx 70) (if (> (/ (+ y yy) 2.0) (/ h 2.0)) (- yy 160) (+ y 160))))
          (list (list (+ x 160) y) (list (+ x 160) yy)) (list (list (- xx 160) y) (list (- xx 160) yy))))
        (setq out (list (list (list (if (< (/ (+ x xx) 2.0) (/ w 2.0)) (+ x 160) (- xx 160)) (+ y 70))
          (list (if (< (/ (+ x xx) 2.0) (/ w 2.0)) (+ x 160) (- xx 160)) (- yy 70)))))))
    ((= k "dining_chair")
      (setq out (list (list (list x (if (< (/ (+ y yy) 2.0) (/ h 2.0)) (+ y 70) (- yy 70)))
        (list xx (if (< (/ (+ y yy) 2.0) (/ h 2.0)) (+ y 70) (- yy 70)))))))
    ((member k '("sink" "basin" "laundry_sink" "washer" "stove" "toilet" "car"))
      (setq out (list (cf:outline (list (+ x (* bw 0.17)) (+ y (* bh 0.17)) (- xx (* bw 0.17)) (- yy (* bh 0.17)))))))
    ((= k "wardrobe") (setq out (list (list (list (/ (+ x xx) 2.0) y) (list (/ (+ x xx) 2.0) yy)))))
    ((= k "shower") (setq out (list (list (list x y) (list xx yy)) (list (list x yy) (list xx y)))))
  )
  (setq pts nil)
  (foreach ln out
    (setq q nil)
    (foreach pt ln (setq pt (cf:pt pt w h rot mir) q (append q (list (list (+ (car zonebox) (car pt)) (+ (cadr zonebox) (cadr pt)))))))
    (setq pts (append pts (list q)))) pts)
(defun cf:choice-index (model zone count / n c)
  (setq n (rem (+ 1.0 (abs (cg:opt "seed" model 1))) 2147483647.0))
  (foreach c (vl-string->list (cg:opt "id" zone "ZONE")) (setq n (rem (+ (* n 31.0) c) 2147483647.0)))
  (setq n (rem (* n 48271.0) 2147483647.0))
  (fix (rem n count)))
(defun cf:place (zone model double / box ww hh rot mir w h temp items it doors candidates attempt *cf-variant*)
  (setq box (cg:get "bounds" zone) ww (- (nth 2 box) (car box)) hh (- (nth 3 box) (cadr box)) doors (cf:doors box model) candidates nil attempt 0)
  (repeat 8
    (setq rot (rem attempt 4) *cf-variant* (fix (/ attempt 4)))
    (setq w (if (= (rem rot 2) 0) ww hh) h (if (= (rem rot 2) 0) hh ww))
    (foreach mir '(nil T)
      (setq temp (cf:template (cg:get "kind" zone) w h double) items nil)
      (foreach it temp
        (setq items (append items (list (list
          (cons "kind" (cg:get "kind" it)) (cons "height" (cg:get "height" it))
          (cons "bounds" (cf:transform (cg:get "bounds" it) box w h rot mir))
          (cons "use_bounds" (cf:transform (cg:get "use_bounds" it) box w h rot mir))
          (cons "rotation" (* rot 90)) (cons "mirror" (if mir 1 0))
          (cons "symbol_lines" (cf:symbol it box w h rot mir))
          (cons "room_id" (cg:opt "room_id" zone (cg:get "id" zone))) (cons "zone_id" (cg:get "id" zone)))))))
      (if (and items (cf:valid items box doors) (cf:window-clear items model) (not (member items candidates)))
        (setq candidates (append candidates (list items)))))
    (setq attempt (1+ attempt)))
  (if candidates (nth (cf:choice-index model zone (length candidates)) candidates) nil))
(defun cf:replace (key val model) (if (assoc key model) (subst (cons key val) (assoc key model) model) (append model (list (cons key val)))))
(defun cg:furnish-model (model params / zones zone items all err beds cap kind num vals result it *cf-occupants* *cf-garage-spaces* doubleCount)
  (setq *cf-occupants* (fix (cg:opt "occupants" params 4)) doubleCount (max 1 (- *cf-occupants* (fix (cg:opt "bedrooms" params 3)))))
  (setq zones (cg:opt "zones" model (cg:get "rooms" model)) all nil err nil beds 0 cap 0 num 0)
  (if (= (cg:opt "furniture" params 1) 1)
    (progn
      (foreach zone zones
        (setq kind (cg:get "kind" zone))
        (if (member kind '("bedroom" "living" "dining" "kitchen" "bathroom" "laundry" "office"))
          (progn
            (setq items (cf:place zone model (and (= kind "bedroom") (< beds doubleCount))))
            (if items (setq all (append all items)) (setq err (strcat "Conjunto funcional nao cabe: " (cg:opt "name" zone kind) ". Ajuste dimensoes ou tente outra alternativa.")))
            (if (= kind "bedroom") (setq cap (+ cap (if (< beds doubleCount) 2 1)) beds (1+ beds))))))
      (foreach zone (cg:get "outdoor" model)
        (if (member (cg:get "kind" zone) '("garage" "veranda" "terrace"))
          (progn (setq *cf-garage-spaces* (fix (cg:opt "spaces" zone 1)) items (cf:place zone model nil))
            (if items (setq all (append all items)) (setq err (strcat "Conjunto externo nao cabe: " (cg:get "kind" zone)))))))
      (if (< cap *cf-occupants*) (setq err "Quantidade de camas insuficiente para moradores. Perfil suporta ate duas pessoas por quarto."))
      (if (> *cf-occupants* 6) (setq err "Perfil de mobiliario atual suporta ate 6 moradores; reduza moradores ou amplie o catalogo de conviv?ncia."))
      (setq result nil)
      (foreach it all (setq num (1+ num) result (append result (list (cons (cons "id" (strcat "F" (itoa num))) it)))))
      (setq vals (append (cg:get "validations" model) (list
        (list (cons "rule_id" "FURNITURE_CLEARANCE") (cons "status" (if err "fail" "pass")) (cons "message" "Limites, sobreposicao, faixas de uso de catalogo, reservas nas portas e pecas altas junto a janelas; nao equivale a acessibilidade."))
        (list (cons "rule_id" "SLEEPING_CAPACITY") (cons "status" (if (>= cap (cg:opt "occupants" params 4)) "pass" "warning")) (cons "message" (strcat "Capacidade de camas: " (itoa cap) ". Moradores informados: " (itoa (fix (cg:opt "occupants" params 4)))))))))
      (if err (list (cons "error" err)) (cf:replace "validations" vals (cf:replace "furniture" result model))))
    (cf:replace "furniture" nil model)))
(princ)












;;; Cobertura conceitual plana: cotas em mm, sem dimensionamento estrutural.
(defun cg:with-roof (model / outline b height w roof)
  (if (cg:get "error" model) model
    (progn
      (setq outline (cg:get "footprint" model))
      (if (not outline) (setq outline (cg:get "outline" (cg:get "slab" model))))
      (if (not outline)
        (progn (setq b (cg:get "house_bounds" model))
          (setq outline (list (list (nth 0 b) (nth 1 b)) (list (nth 2 b) (nth 1 b))
            (list (nth 2 b) (nth 3 b)) (list (nth 0 b) (nth 3 b))))))
      (setq height 0.0)
      (foreach w (cg:get "walls" model) (setq height (max height (cg:get "height" w))))
      (setq roof (list (cons "kind" "flat_slab") (cons "outline" outline)
        (cons "base_z" height) (cons "thickness" 150.0)
        (cons "parapet_height" 600.0) (cons "parapet_thickness" 100.0)
        (cons "note" "Cobertura conceitual: caimentos, drenagem, impermeabilizacao e estrutura a projetar.")))
      (if (assoc "roof" model) (subst (cons "roof" roof) (assoc "roof" model) model)
        (append model (list (cons "roof" roof)))))))
(princ)

;;; Sections and roof representation, all coordinates in millimetres.
(defun cd:polyline (points closed layer id)
 (cg:mk (append (list '(0 . "LWPOLYLINE") '(100 . "AcDbEntity") (cons 8 layer)
  '(100 . "AcDbPolyline") (cons 90 (length points)) (cons 70 (if closed 1 0)))
  (mapcar '(lambda (p) (cons 10 p)) points)) id))
(defun cd:intervals (poly y / points a b xs result)
 (setq points (append poly (list (car poly))) xs nil result nil)
 (while (cdr points)
  (setq a (car points) b (cadr points))
  (if (and (equal (car a) (car b) 0.01) (<= (min (cadr a) (cadr b)) y) (> (max (cadr a) (cadr b)) y))
   (setq xs (cons (car a) xs)))
  (setq points (cdr points)))
 (setq xs (vl-sort xs '<))
 (while (cdr xs) (setq result (append result (list (list (car xs) (cadr xs)))) xs (cddr xs))) result)
(defun cd:sections (model tx yy / roof poly house x0 x1 y0 y1 ht rt ph pt cutY spans pair lo hi item a b w op gap c sill top left right room facadeY)
 (setq roof (cg:get "roof" model) poly (cg:get "outline" roof) house (cg:get "house_bounds" model)
  x0 (nth 0 house) y0 (nth 1 house) x1 (nth 2 house) y1 (nth 3 house)
  ht (cg:get "base_z" roof) rt (cg:get "thickness" roof) ph (cg:get "parapet_height" roof) pt (cg:get "parapet_thickness" roof)
  cutY (+ y0 (* 0.37 (- y1 y0))) yy (- yy ht ph 2000) spans (cd:intervals poly cutY))
 (cg:text (list tx (+ yy ht rt ph 500)) "CORTE A-A | laje de cobertura e platibanda" 200 "CASA_TEXTOS" "SECTION")
 (foreach pair spans
  (setq lo (+ tx (- (car pair) x0)) hi (+ tx (- (cadr pair) x0)))
  (cg:rect (list lo (- yy (cg:get "thickness" (cg:get "slab" model))) hi yy) "CASA_ESTUDO" "SECTION-FLOOR")
  (cg:rect (list lo (+ yy ht) hi (+ yy ht rt)) "CASA_COBERTURA" "SECTION-ROOF")
  (cg:rect (list lo (+ yy ht rt) (+ lo pt) (+ yy ht rt ph)) "CASA_COBERTURA" "SECTION-PARAPET")
  (cg:rect (list (- hi pt) (+ yy ht rt) hi (+ yy ht rt ph)) "CASA_COBERTURA" "SECTION-PARAPET"))
 (foreach item (cg:get "walls" model)
  (setq a (cg:get "start" item) b (cg:get "end" item) w (cg:get "thickness" item) gap nil)
  (if (and (equal (car a) (car b) 0.01) (< (min (cadr a) (cadr b)) cutY) (> (max (cadr a) (cadr b)) cutY))
   (progn
    (foreach op (cg:get "openings" model)
     (if (and (= (cg:get "wall_id" op) (cg:get "id" item))
       (< (abs (- (cadr (cg:get "center" op)) cutY)) (/ (cg:get "width" op) 2))) (setq gap op)))
    (setq left (+ tx (- (car a) x0 (/ w 2))) right (+ left w))
    (if gap
     (progn (setq sill (cg:get "sill" gap) top (+ sill (cg:get "height" gap)))
      (if (> sill 0) (cg:rect (list left yy right (+ yy sill)) "CASA_ESTUDO" "SECTION-WALL"))
      (if (< top ht) (cg:rect (list left (+ yy top) right (+ yy ht)) "CASA_ESTUDO" "SECTION-WALL"))
      (if (= (cg:get "kind" gap) "window") (cg:line (list (/ (+ left right) 2) (+ yy sill)) (list (/ (+ left right) 2) (+ yy top)) "CASA_JANELAS" "SECTION-WINDOW")))
     (cg:rect (list left yy right (+ yy ht)) "CASA_ESTUDO" "SECTION-WALL")))))
 (cg:dim (list tx yy) (list tx (+ yy ht)) (list (- tx 600) yy) "DIM-CEILING")
 (cg:dim (list (+ tx (- x1 x0)) yy) (list (+ tx (- x1 x0)) (+ yy ht rt ph)) (list (+ tx (- x1 x0) 600) yy) "DIM-TOTAL-HEIGHT")
 (cg:text (list tx (- yy 500)) "Laje conceitual 15 cm. Caimento, drenagem e estrutura a dimensionar." 140 "CASA_TEXTOS" "ROOF-NOTE")
 (cg:line (list (- x0 250) cutY) (list (+ x1 250) cutY) "CASA_ESTUDO" "SECTION-MARK")
 (cg:text (list (- x0 500) (+ cutY 150)) "A" 180 "CASA_TEXTOS" "SECTION-MARK")
 (cg:text (list (+ x1 300) (+ cutY 150)) "A" 180 "CASA_TEXTOS" "SECTION-MARK")
 (setq yy (- yy ht rt ph 2000))
 (cg:text (list tx (+ yy ht rt ph 500)) "FACHADA FRONTAL | cobertura com platibanda" 200 "CASA_TEXTOS" "FACADE")
 (cg:rect (list tx yy (+ tx (- x1 x0)) (+ yy ht)) "CASA_ESTUDO" "FACADE")
 (cg:rect (list tx (+ yy ht) (+ tx (- x1 x0)) (+ yy ht rt)) "CASA_COBERTURA" "FACADE-ROOF")
 (cg:rect (list tx (+ yy ht rt) (+ tx (- x1 x0)) (+ yy ht rt ph)) "CASA_COBERTURA" "FACADE-PARAPET")
 (foreach item (cg:get "openings" model)
  (setq a (cg:find-id (cg:get "wall_id" item) (cg:get "walls" model)) c (cg:get "center" item)
   room (cg:find-id (cg:get "room_id" item) (cg:get "rooms" model)))
  (if (and (= (cg:get "wall_role" a) "external")
    (equal (cadr (cg:get "start" a)) (cadr (cg:get "end" a)) 0.01)
    room (> (cadr (cg:get "bounds" room)) (cadr c)))
   (progn (setq w (cg:get "width" item) sill (cg:get "sill" item))
    (cg:rect (list (+ tx (- (car c) x0 (/ w 2))) (+ yy sill)
     (+ tx (- (+ (car c) (/ w 2)) x0)) (+ yy sill (cg:get "height" item))) "CASA_ESTUDO" "FACADE-OPENING"))))
 (princ))
(princ)

;;; Union boundary of orthogonal wall solids, with openings retained.
(defun cj:inside (p boxes / found b)
 (setq found nil)
 (foreach b boxes (if (and (> (car p) (car b)) (< (car p) (nth 2 b))
  (> (cadr p) (cadr b)) (< (cadr p) (nth 3 b))) (setq found T))) found)
(defun cj:extension (p walls / other a b result)
 (setq result 0.0)
 (foreach other walls
  (setq a (cg:get "start" other) b (cg:get "end" other))
  (if (and (equal (car a) (car b) 0.01) (equal (car p) (car a) 0.01)
    (<= (- (min (cadr a) (cadr b)) 0.01) (cadr p))
    (>= (+ (max (cadr a) (cadr b)) 0.01) (cadr p)))
   (setq result (max result (/ (cg:get "thickness" other) 2.0))))) result)
(defun cj:boxes (walls openings / result w a b h horizontal low high gaps o c gap pos ext0 ext1)
 (setq result nil)
 (foreach w walls
  (setq a (cg:get "start" w) b (cg:get "end" w) h (/ (cg:get "thickness" w) 2.0)
   horizontal (equal (cadr a) (cadr b) 0.01) gaps nil)
  (if horizontal
   (setq low (min (car a) (car b)) high (max (car a) (car b))
    ext0 (cj:extension (list low (cadr a)) walls) ext1 (cj:extension (list high (cadr a)) walls))
   (setq low (min (cadr a) (cadr b)) high (max (cadr a) (cadr b)) ext0 0.0 ext1 0.0))
  (foreach o openings (if (= (cg:get "wall_id" o) (cg:get "id" w))
   (progn (setq c (if horizontal (car (cg:get "center" o)) (cadr (cg:get "center" o))))
    (setq gaps (cons (list (- c (/ (cg:get "width" o) 2.0)) (+ c (/ (cg:get "width" o) 2.0))) gaps)))))
  (setq pos (- low ext0) gaps (append (vl-sort gaps '(lambda (u v) (< (car u) (car v)))) (list (list (+ high ext1) (+ high ext1)))))
  (foreach gap gaps
   (if (> (- (car gap) pos) 0.01)
    (setq result (cons (if horizontal (list pos (- (cadr a) h) (car gap) (+ (cadr a) h))
     (list (- (car a) h) pos (+ (car a) h) (car gap))) result)))
   (setq pos (max pos (cadr gap))))) result)
(defun cj:edge (horizontal fixed low high boxes / cuts b value vals p q mid one two result)
 (setq cuts (list low high) result nil)
 (foreach b boxes
  (foreach value (if horizontal (list (car b) (nth 2 b)) (list (cadr b) (nth 3 b)))
   (if (and (> value low) (< value high)) (setq cuts (cons value cuts)))))
 (setq vals (vl-sort cuts '<))
 (while (cdr vals)
  (setq p (car vals) q (cadr vals) mid (/ (+ p q) 2.0)
   one (if horizontal (list mid (- fixed 0.005)) (list (- fixed 0.005) mid))
   two (if horizontal (list mid (+ fixed 0.005)) (list (+ fixed 0.005) mid)))
  (if (and (> (- q p) 0.01) (not (eq (cj:inside one boxes) (cj:inside two boxes))))
   (setq result (cons (if horizontal (list (list p fixed) (list q fixed)) (list (list fixed p) (list fixed q))) result)))
  (setq vals (cdr vals))) result)
(defun cj:segments (boxes / result b edge segment)
 (setq result nil)
 (foreach b boxes
  (foreach edge (list (list T (cadr b) (car b) (nth 2 b)) (list T (nth 3 b) (car b) (nth 2 b))
    (list nil (car b) (cadr b) (nth 3 b)) (list nil (nth 2 b) (cadr b) (nth 3 b)))
   (foreach segment (cj:edge (car edge) (cadr edge) (nth 2 edge) (nth 3 edge) boxes)
    (if (not (member segment result)) (setq result (cons segment result)))))) result)
(defun cj:draw (model / segment)
 (foreach segment (cj:segments (cj:boxes (cg:get "walls" model) (cg:get "openings" model)))
  (cg:line (car segment) (cadr segment) "CASA_PAREDES" "WALL-UNION")))

;;; Choose dimension lines in the least occupied strip of each room.
(defun cj:position (b horizontal model / ratio pos low high strip score best bestscore obj box area)
 (setq bestscore 1e99 best nil)
 (foreach ratio '(0.12 0.88 0.25 0.75 0.4 0.6 0.5)
  (setq low (if horizontal (cadr b) (car b)) high (if horizontal (nth 3 b) (nth 2 b))
   pos (+ low (* ratio (- high low)))
   strip (if horizontal (list (car b) (- pos 60) (nth 2 b) (+ pos 230))
    (list (- pos 230) (cadr b) (+ pos 60) (nth 3 b))) score 0.0)
  (foreach box (append (mapcar '(lambda (f) (cg:get "bounds" f)) (cg:get "furniture" model)) *cj-label-boxes* (cf:doors b model))
   (setq area (* (max 0 (- (min (nth 2 strip) (nth 2 box)) (max (car strip) (car box))))
     (max 0 (- (min (nth 3 strip) (nth 3 box)) (max (cadr strip) (cadr box))))))
   (setq score (+ score area)))
  (if (< score bestscore) (setq bestscore score best pos))) best)
;;; Clear room dimensions stay with their room, overall dimensions outside lot.
(defun cj:dimensions (model / room b site house x0 y0 x1 y1 id dx dy pts a z)
 (setq site (cg:get "site_bounds" model) house (cg:get "house_bounds" model)
  x0 (car house) y0 (cadr house) x1 (nth 2 house) y1 (nth 3 house))
 (foreach room (cg:get "rooms" model)
  (setq b (cg:get "bounds" room) id (cg:get "id" room)
   dy (cj:position b T model) dx (cj:position b nil model))
  (cg:dim (list (car b) dy) (list (nth 2 b) dy)
   (list (car b) dy) (strcat "DX-CLEAR-" id))
  (if (/= (cg:get "kind" room) "corridor")
   (cg:dim (list dx (cadr b)) (list dx (nth 3 b))
    (list dx (cadr b)) (strcat "DY-CLEAR-" id))))
 ;; Locate the inset edges from the actual footprint, not its bounding box.
 (setq pts (append (cg:get "footprint" model) (list (car (cg:get "footprint" model)))))
 (while (cdr pts)
  (setq a (car pts) z (cadr pts))
  (cond
   ((and (equal (cadr a) (cadr z) 0.01) (> (cadr a) (+ y0 1)) (< (cadr a) (- y1 1)))
    (cg:dim a z (list (car a) (+ (cadr a) (if (> (cadr a) (/ (+ y0 y1) 2)) 600 -600))) "DIM-RECESS-W"))
   ((and (equal (car a) (car z) 0.01) (> (car a) (+ x0 1)) (< (car a) (- x1 1)))
    (cg:dim a z (list (if (> (car a) (/ (+ x0 x1) 2)) (+ x1 600) (- x0 600)) (cadr a)) "DIM-RECESS-D")))
  (setq pts (cdr pts)))
 (cg:dim (list x0 y0) (list x1 y0) (list x0 (- (cadr site) 700)) "DIM-HOUSE-W")
 (cg:dim (list x0 y0) (list x0 y1) (list (- (car site) 700) y0) "DIM-HOUSE-D")
 (cg:dim (list (car site) (cadr site)) (list (nth 2 site) (cadr site))
  (list (car site) (- (cadr site) 1400)) "DIM-SITE-W")
 (cg:dim (list (nth 2 site) (cadr site)) (list (nth 2 site) (nth 3 site))
  (list (+ (nth 2 site) 1500) (cadr site)) "DIM-SITE-D"))

(defun cg:embedded-dialog (/ file stream)
 (setq file (vl-filename-mktemp "casa-bh-" nil ".dcl") stream (open file "w"))
 (write-line "casa_form : dialog {" stream)
 (write-line " label = \"CASA BH - estudo preliminar 0.4\";" stream)
 (write-line " : text { label = \"Casa terrea | terreno hipotetico plano | medidas em metros\"; }" stream)
 (write-line " : row {" stream)
 (write-line "  : boxed_column { label = \"Terreno e construcao\";" stream)
 (write-line "   : edit_box { key = \"lot_width\"; label = \"Largura lote\"; edit_width = 10; }" stream)
 (write-line "   : edit_box { key = \"lot_depth\"; label = \"Profundidade lote\"; edit_width = 10; }" stream)
 (write-line "   : edit_box { key = \"house_width\"; label = \"Largura casa\"; edit_width = 10; }" stream)
 (write-line "   : edit_box { key = \"wall_internal\"; label = \"Parede interna\"; edit_width = 10; }" stream)
 (write-line "   : edit_box { key = \"wall_external\"; label = \"Parede externa\"; edit_width = 10; }" stream)
 (write-line "   : edit_box { key = \"height\"; label = \"Pe-direito\"; edit_width = 10; }" stream)
 (write-line "   : edit_box { key = \"corridor\"; label = \"Largura corredor\"; edit_width = 10; }" stream)
 (write-line "  }" stream)
 (write-line "  : boxed_column { label = \"Ambientes (quantidades obrigatorias)\";" stream)
 (write-line "   : edit_box { key = \"bedrooms\"; label = \"Quartos\"; edit_width = 6; }" stream)
 (write-line "   : edit_box { key = \"bathrooms\"; label = \"Banheiros sociais\"; edit_width = 6; }" stream)
 (write-line "   : edit_box { key = \"living\"; label = \"Salas de estar\"; edit_width = 6; }" stream)
 (write-line "   : edit_box { key = \"kitchens\"; label = \"Cozinhas\"; edit_width = 6; }" stream)
 (write-line "   : edit_box { key = \"laundry\"; label = \"Lavanderias\"; edit_width = 6; }" stream)
 (write-line "   : edit_box { key = \"dining\"; label = \"Salas de jantar\"; edit_width = 6; }" stream)
 (write-line "   : edit_box { key = \"office\"; label = \"Escritorios\"; edit_width = 6; }" stream)
 (write-line "  }" stream)
 (write-line " }" stream)
 (write-line " : boxed_row { label = \"Faixas livres de ENSAIO - nao sao recuos legais de BH\";" stream)
 (write-line "  : edit_box { key = \"front\"; label = \"Frente\"; edit_width = 7; }" stream)
 (write-line "  : edit_box { key = \"rear\"; label = \"Fundos\"; edit_width = 7; }" stream)
 (write-line "  : edit_box { key = \"side\"; label = \"Laterais\"; edit_width = 7; }" stream)
 (write-line " }" stream)
 (write-line " : row {" stream)
 (write-line "  : edit_box { key = \"seed\"; label = \"Semente da alternativa\"; edit_width = 12; }" stream)
 (write-line "  : toggle { key = \"furniture\"; label = \"Inserir mobiliario esquematico\"; }" stream)
 (write-line " }" stream)
 (write-line " : boxed_row { label = \"Moradores e alternativas\";" stream)
 (write-line "  : edit_box { key = \"occupants\"; label = \"Moradores (1-6)\"; edit_width = 4; }" stream)
 (write-line "  : edit_box { key = \"parking\"; label = \"Vagas (0-2)\"; edit_width = 4; }" stream)
 (write-line "  : edit_box { key = \"north\"; label = \"Norte em graus (0=+Y)\"; edit_width = 5; }" stream)
 (write-line " }" stream)
 (write-line " : row {" stream)
 (write-line "  : popup_list { key = \"layout\"; label = \"Organizacao\"; width = 27; }" stream)
 (write-line "  : popup_list { key = \"integration\"; label = \"Integracao social\"; width = 24; }" stream)
 (write-line "  : toggle { key = \"terrace\"; label = \"Convivencia externa\"; }" stream)
 (write-line " }" stream)
 (write-line " : text { label = \"Garagem descoberta; norte informado/hipotetico. Laje conceitual com platibanda; sem suites.\"; }" stream)
 (write-line " : text { label = \"Edicoes manuais CAD nao sao sincronizadas. Desempenho ambiental nao simulado.\"; }" stream)
 (write-line " : text { label = \"Com vaga: frente efetiva de ao menos 6.50 m para carro e acesso pedestre.\"; }" stream)
 (write-line " : text { key = \"error\"; label = \"\"; width = 95; }" stream)
 (write-line " ok_cancel;" stream)
 (write-line "}" stream)
 (close stream) (setq *casa-temp-dcl* file) file)

;;; CASA BH - AutoCAD 2027 / AutoLISP. ASCII source for legacy LISPSYS.
(vl-load-com)
(setq *casa-version* "0.4.0")
(setq *casa-fields* '("lot_width" "lot_depth" "house_width" "wall_internal" "wall_external" "height" "corridor"
  "bedrooms" "bathrooms" "living" "kitchens" "laundry" "dining" "office" "front" "rear" "side" "seed" "occupants" "parking" "layout" "integration" "north"))
(if (not *casa-input*)
 (setq *casa-input* '(("lot_width" . "12") ("lot_depth" . "30") ("house_width" . "9")
  ("wall_internal" . "0.15") ("wall_external" . "0.20") ("height" . "2.8") ("corridor" . "1.2") ("bedrooms" . "3")
  ("bathrooms" . "1") ("living" . "1") ("kitchens" . "1") ("laundry" . "1")
  ("dining" . "1") ("office" . "0") ("front" . "6.5") ("rear" . "3") ("side" . "1.5")
  ("seed" . "42") ("furniture" . "1"))))
(foreach pair '(("wall_internal" . "0.15") ("wall_external" . "0.20") ("occupants" . "4") ("parking" . "1") ("layout" . "0") ("integration" . "0") ("north" . "0") ("terrace" . "1"))
 (if (not (assoc (car pair) *casa-input*)) (setq *casa-input* (cons pair *casa-input*))))
(defun cg:ensure-core () T)
(defun cg:accept (/ key raw value params inputs err lengthkeys)
 (setq params nil inputs nil err nil lengthkeys '("lot_width" "lot_depth" "house_width" "wall_internal" "wall_external" "height" "corridor" "front" "rear" "side"))
 (foreach key *casa-fields*
  (setq raw (get_tile key) value (distof (vl-string-translate "," "." raw) 2))
  (setq inputs (cons (cons key raw) inputs))
  (if value
   (setq params (cons (cons key (if (member key lengthkeys) (* value 1000.0) value)) params))
   (setq err (strcat "Preencha um numero valido em: " key))))
 (setq params (cons (cons "terrace" (atoi (get_tile "terrace"))) params) inputs (cons (cons "terrace" (get_tile "terrace")) inputs))
 (setq params (cons (cons "furniture" (atoi (get_tile "furniture"))) params)
       inputs (cons (cons "furniture" (get_tile "furniture")) inputs))
 (if (not err) (setq err (cg:validate-input params)))
 (if err (set_tile "error" err)
  (progn (setq *casa-input* inputs *casa-params* params) (done_dialog 1))))
(defun cg:form (/ dlg result pair)
 (setq dlg (load_dialog (cg:embedded-dialog)))
 (if (and (> dlg 0) (new_dialog "casa_form" dlg))
  (progn
   (start_list "layout") (mapcar 'add_list '("Aleatoria" "Social na frente" "Social no fundo" "Nucleo de convivencia")) (end_list)
   (start_list "integration") (mapcar 'add_list '("Variar" "Aberta" "Semiaberta" "Fechada")) (end_list)
   (foreach pair *casa-input* (set_tile (car pair) (cdr pair)))
   (action_tile "accept" "(cg:accept)")
   (action_tile "cancel" "(done_dialog 0)")
   (setq result (start_dialog)) (progn (unload_dialog dlg) (if *casa-temp-dcl* (vl-file-delete *casa-temp-dcl*))) (= result 1))
  (progn (if (> dlg 0) (progn (unload_dialog dlg) (if *casa-temp-dcl* (vl-file-delete *casa-temp-dcl*)))) (alert "Nao foi possivel abrir casa.dcl.") nil)))
(defun cg:escape (str / i ch out)
 (setq i 1 out "")
 (repeat (strlen str)
  (setq ch (substr str i 1) out (strcat out
   (cond ((= ch "\"") "\\\"") ((= ch "\\") "\\\\") ((= ch (chr 10)) "\\n")
    ((= ch (chr 13)) "\\r") ((= ch (chr 9)) "\\t") (T ch))) i (1+ i))) out)
(defun cg:join (items separator / out item)
 (setq out "") (foreach item items (setq out (strcat out (if (= out "") "" separator) item))) out)
(defun cg:number-json (value / text)
 (setq text (rtos value 2 6))
 (if (= (substr text 1 1) ".") (setq text (strcat "0" text)))
 (if (= (substr text 1 2) "-.") (setq text (strcat "-0" (substr text 2)))) text)
(defun cg:json (value / pair out)
 (cond ((eq value 'cj:true) "true") ((eq value 'cj:false) "false") ((eq value 'cj:null) "null") ((null value) "[]")
  ((= (type value) 'STR) (strcat "\"" (cg:escape value) "\""))
  ((numberp value) (cg:number-json value))
  ((and (listp value) (listp (car value)) (= (type (caar value)) 'STR))
   (setq out nil)
   (foreach pair value (setq out (append out (list (strcat (cg:json (car pair)) ":" (cg:json (cdr pair)))))))
   (strcat "{" (cg:join out ",") "}"))
  ((listp value) (strcat "[" (cg:join (mapcar 'cg:json value) ",") "]"))
  (T "null")))
(defun cg:write-json (model file / stream)
 (setq stream (open file "w"))
 (if stream (progn (write-line (cg:json model) stream) (close stream) T) nil))
(defun cg:tag (entity id / data)
 (if entity
  (progn (setq data (entget entity))
   (entmod (append data (list (list -3 (list "CASA_BH" (cons 1000 *cg-pid*) (cons 1000 id)))))) entity)))
(defun cg:mk (data id / entity)
 (setq entity (entmakex data))
 (if (not entity) (progn (princ "\nFalha ao criar entidade. Operacao cancelada.") (exit)))
 (cg:tag entity id))
(defun cg:layer (name color)
 (if (not (tblsearch "LAYER" name))
  (entmake (list '(0 . "LAYER") '(100 . "AcDbSymbolTableRecord") '(100 . "AcDbLayerTableRecord")
   (cons 2 name) '(70 . 0) (cons 62 color) '(6 . "Continuous")))))
(defun cg:line (a b layer id)
 (cg:mk (list '(0 . "LINE") (cons 8 layer) (cons 10 (append a '(0.0))) (cons 11 (append b '(0.0)))) id))
(defun cg:rect (box layer id / x0 y0 x1 y1)
 (setq x0 (nth 0 box) y0 (nth 1 box) x1 (nth 2 box) y1 (nth 3 box))
 (cg:mk (list '(0 . "LWPOLYLINE") '(100 . "AcDbEntity") (cons 8 layer)
  '(100 . "AcDbPolyline") '(90 . 4) '(70 . 1)
  (cons 10 (list x0 y0)) (cons 10 (list x1 y0)) (cons 10 (list x1 y1)) (cons 10 (list x0 y1))) id))
(defun cg:text (point str size layer id)
 (cg:mk (list '(0 . "TEXT") (cons 8 layer) (cons 10 (append point '(0.0))) (cons 40 size)
  (cons 1 str) '(50 . 0.0) '(7 . "Standard")) id))
(defun cg:dim (a b point id)
 (setvar "CLAYER" "CASA_COTAS")
 (command-s "_.DIMLINEAR" "_non" (append a '(0.0)) "_non" (append b '(0.0)) "_non" (append point '(0.0)))
 (cg:tag (entlast) id))
(defun cg:wall-segment (start end lo hi thick horizontal id / x y)
 (if (> (- hi lo) 0.1)
  (if horizontal
   (cg:rect (list (+ (car start) lo) (- (cadr start) (/ thick 2.0))
    (+ (car start) hi) (+ (cadr start) (/ thick 2.0))) "CASA_PAREDES" id)
   (cg:rect (list (- (car start) (/ thick 2.0)) (+ (cadr start) lo)
    (+ (car start) (/ thick 2.0)) (+ (cadr start) hi)) "CASA_PAREDES" id))))
(defun cg:draw-wall (wall openings / a b horiz len intervals opening at current gap thick id)
 (setq a (cg:get "start" wall) b (cg:get "end" wall) horiz (equal (cadr a) (cadr b) 0.01)
  len (distance a b) thick (cg:get "thickness" wall) id (cg:get "id" wall) intervals nil current 0.0)
 (foreach opening openings
  (if (= (cg:get "wall_id" opening) id)
   (progn
    (setq at (distance a (cg:get "center" opening)))
    (setq intervals (cons (list (- at (/ (cg:get "width" opening) 2.0))
      (+ at (/ (cg:get "width" opening) 2.0))) intervals)))))
 (setq intervals (vl-sort intervals '(lambda (u v) (< (car u) (car v)))))
 (foreach gap intervals
  (cg:wall-segment a b current (car gap) thick horiz id)
  (setq current (cadr gap)))
 (cg:wall-segment a b current len thick horiz id))
(defun cg:find-id (id records / result record)
 (setq result nil) (foreach record records (if (= id (cg:get "id" record)) (setq result record))) result)
(defun cg:draw-opening (opening walls / wall c width horiz a b h id hinge tip angle0 angle1 roomside)
 (setq wall (cg:find-id (cg:get "wall_id" opening) walls) c (cg:get "center" opening)
  width (cg:get "width" opening) h (/ (cg:get "thickness" wall) 2.0)
  horiz (equal (cadr (cg:get "start" wall)) (cadr (cg:get "end" wall)) 0.01)
  id (cg:get "id" opening))
 (if horiz
  (setq a (list (- (car c) (/ width 2.0)) (cadr c)) b (list (+ (car c) (/ width 2.0)) (cadr c)))
  (setq a (list (car c) (- (cadr c) (/ width 2.0))) b (list (car c) (+ (cadr c) (/ width 2.0)))))
 (if (= (cg:get "kind" opening) "window")
  (progn
   (cg:line a b "CASA_JANELAS" id)
   (if horiz
    (progn (cg:line (list (car a) (- (cadr a) h)) (list (car b) (- (cadr b) h)) "CASA_JANELAS" id)
     (cg:line (list (car a) (+ (cadr a) h)) (list (car b) (+ (cadr b) h)) "CASA_JANELAS" id))
    (progn (cg:line (list (- (car a) h) (cadr a)) (list (- (car b) h) (cadr b)) "CASA_JANELAS" id)
     (cg:line (list (+ (car a) h) (cadr a)) (list (+ (car b) h) (cadr b)) "CASA_JANELAS" id))))
  (progn
   (setq hinge a)
   (if horiz
    (setq tip (list (car a) (+ (cadr a) width)) angle0 0.0 angle1 (/ pi 2.0))
    (progn
     (setq roomside (cg:find-id (cg:get "room_id" opening) (cg:get "rooms" *cg-drawing-model*)))
     (if (< (nth 0 (cg:get "bounds" roomside)) (car c))
      (setq tip (list (- (car a) width) (cadr a)) angle0 (/ pi 2.0) angle1 pi)
      (setq tip (list (+ (car a) width) (cadr a)) angle0 0.0 angle1 (/ pi 2.0)))))
   (cg:line hinge tip "CASA_PORTAS" id)
   (cg:mk (list '(0 . "ARC") '(8 . "CASA_PORTAS") (cons 10 (append hinge '(0.0)))
    (cons 40 width) (cons 50 angle0) (cons 51 angle1)) id))))
(defun cg:draw-furniture (item / box kind id)
 (setq box (cg:get "bounds" item) kind (cg:get "kind" item) id (cg:get "id" item))
 (cg:rect box "CASA_MOVEIS" id)
 (cond
  ((= kind "bed")
   (cg:rect (list (+ (nth 0 box) 100) (- (nth 3 box) 500) (- (nth 2 box) 100) (- (nth 3 box) 100)) "CASA_MOVEIS" id))
  ((= kind "sofa")
   (cg:rect (list (+ (nth 0 box) 100) (+ (nth 1 box) 100) (- (nth 2 box) 100) (- (nth 3 box) 200)) "CASA_MOVEIS" id))
  ((= kind "shower")
   (cg:line (list (nth 0 box) (nth 1 box)) (list (nth 2 box) (nth 3 box)) "CASA_MOVEIS" id))))
(defun cg:draw-model (model / site house walls openings rooms item box x0 y0 x1 y1 tx ty lineY i total clearbox ht wt it)
 (setq *cg-drawing-model* model site (cg:get "site_bounds" model) house (cg:get "house_bounds" model)
  walls (cg:get "walls" model) openings (cg:get "openings" model) rooms (cg:get "rooms" model)
  x0 (nth 0 house) y0 (nth 1 house) x1 (nth 2 house) y1 (nth 3 house))
 (foreach item '(("CASA_LOTE" 8) ("CASA_PAREDES" 7) ("CASA_PORTAS" 2) ("CASA_JANELAS" 4)
   ("CASA_MOVEIS" 3) ("CASA_TEXTOS" 7) ("CASA_COTAS" 6) ("CASA_ESTUDO" 8)) (cg:layer (car item) (cadr item)))
 (cg:rect site "CASA_LOTE" "SITE")
 (foreach item walls (cg:draw-wall item openings))
 (foreach item openings (cg:draw-opening item walls))
 (foreach item (cg:get "furniture" model) (cg:draw-furniture item))
 (foreach item rooms
  (setq box (cg:get "bounds" item))
  (if (/= (cg:get "kind" item) "corridor")
   (progn
    (cg:text (list (+ (nth 0 box) (if (> (nth 0 box) (/ (+ x0 x1) 2.0)) 1100 150)) (+ (nth 1 box) 350))
     (strcat (cg:get "id" item) " " (cg:get "name" item)) 150 "CASA_TEXTOS" (cg:get "id" item))
    (cg:text (list (+ (nth 0 box) (if (> (nth 0 box) (/ (+ x0 x1) 2.0)) 1100 150)) (+ (nth 1 box) 120))
     (strcat (rtos (cg:get "net_area_m2" item) 2 2) " m2") 120 "CASA_TEXTOS" (cg:get "id" item))
    (if (equal (nth 0 box) (+ x0 (cg:get "thickness" (car walls))) 0.01)
     (cg:dim (list (nth 0 box) (nth 1 box)) (list (nth 0 box) (nth 3 box))
      (list (- x0 600) (/ (+ (nth 1 box) (nth 3 box)) 2.0)) "DIM-ROOM")))))
 (foreach item (list (nth 0 rooms) (nth 1 rooms) (cg:find-id "CIRC" rooms))
  (setq box (cg:get "bounds" item))
  (cg:dim (list (nth 0 box) y0) (list (nth 2 box) y0)
   (list (nth 0 box) (- y0 450)) "DIM-CLEAR-W"))
 (cg:dim (list x0 y0) (list x1 y0) (list x0 (- y0 1000)) "DIM-HOUSE-W")
 (cg:dim (list x0 y0) (list x0 y1) (list (- x0 1300) y0) "DIM-HOUSE-D")
 (cg:dim (list (nth 0 site) (nth 1 site)) (list (nth 2 site) (nth 1 site))
  (list (nth 0 site) (- (nth 1 site) 1500)) "DIM-SITE-W")
 (cg:dim (list (nth 2 site) (nth 1 site)) (list (nth 2 site) (nth 3 site))
  (list (+ (nth 2 site) 1200) (nth 1 site)) "DIM-SITE-D")
 (setq tx (+ (nth 2 site) 3500) ty (nth 3 site) lineY (- ty 800) total 0.0)
 (cg:text (list tx ty) "CASA BH | ESTUDO PRELIMINAR" 300 "CASA_TEXTOS" "TITLE")
 (cg:text (list tx (- ty 450)) (strcat "Projeto " (cg:get "project_id" model) " | seed " (itoa (fix (cg:get "seed" model)))) 180 "CASA_TEXTOS" "TITLE")
 (foreach item rooms
  (cg:text (list tx lineY) (strcat (cg:get "id" item) " - " (cg:get "name" item) " : "
    (rtos (cg:get "net_area_m2" item) 2 2) " m2") 180 "CASA_TEXTOS" "SCHEDULE")
  (setq lineY (- lineY 320) total (+ total (cg:get "net_area_m2" item))))
 (cg:text (list tx (- lineY 150)) (strcat "Area util: " (rtos total 2 2) " m2 | Construida geometrica: "
   (rtos (cg:get "gross_area_m2" model) 2 2) " m2") 180 "CASA_TEXTOS" "SCHEDULE")
 (setq lineY (- lineY 600))
 (foreach item '("Nao aprovado pela PBH. Faixas livres sao parametros de ensaio."
   "Cotas em metros; geometria em milimetros. Terreno plano hipotetico."
   "Norte, levantamento, cobertura, estrutura e instalacoes: a definir."
   "Mobiliario esquematico. Operacao e acessibilidade nao verificadas."
   "Revit: exportar snapshot gerado; alteracoes manuais CAD nao seguem.")
  (cg:text (list tx lineY) item 160 "CASA_TEXTOS" "NOTES") (setq lineY (- lineY 300)))
 ;; Schematic section and facade, deliberately not construction details.
 (setq lineY (- lineY 4500) ht (cg:get "height" (car walls)) wt (cg:get "thickness" (car walls)) it (cg:opt "wall_internal" model wt))
 (cg:text (list tx (+ lineY ht 550)) "CORTE A-A ESQUEMATICO | cobertura a definir" 220 "CASA_TEXTOS" "SECTION")
 (cg:rect (list tx (- lineY 150) (+ tx (- x1 x0)) lineY) "CASA_ESTUDO" "SECTION")
 (cg:rect (list tx lineY (+ tx wt) (+ lineY ht)) "CASA_ESTUDO" "SECTION")
 (cg:rect (list (- (+ tx (- x1 x0)) wt) lineY (+ tx (- x1 x0)) (+ lineY ht)) "CASA_ESTUDO" "SECTION")
 (setq clearbox (cg:get "bounds" (cg:find-id "CIRC" rooms)))
 (cg:rect (list (+ tx (- (nth 0 clearbox) x0 it)) lineY (+ tx (- (nth 0 clearbox) x0)) (+ lineY ht)) "CASA_ESTUDO" "SECTION")
 (cg:rect (list (+ tx (- (nth 2 clearbox) x0)) lineY (+ tx (- (nth 2 clearbox) x0) it) (+ lineY ht)) "CASA_ESTUDO" "SECTION")
 (cg:line (list tx (+ lineY ht)) (list (+ tx (- x1 x0)) (+ lineY ht)) "CASA_ESTUDO" "SECTION")
 (cg:dim (list tx lineY) (list tx (+ lineY ht)) (list (- tx 650) lineY) "DIM-HEIGHT")
 (cg:line (list (- x0 300) (+ y0 1600)) (list (+ x1 300) (+ y0 1600)) "CASA_ESTUDO" "SECTION-MARK")
 (cg:text (list (- x0 350) (+ y0 1850)) "A" 200 "CASA_TEXTOS" "SECTION-MARK")
 (cg:text (list (+ x1 200) (+ y0 1850)) "A" 200 "CASA_TEXTOS" "SECTION-MARK")
 (setq lineY (- lineY 5000))
 (cg:text (list tx (+ lineY ht 550)) "FACHADA FRONTAL ESQUEMATICA" 220 "CASA_TEXTOS" "FACADE")
 (cg:rect (list tx lineY (+ tx (- x1 x0)) (+ lineY ht)) "CASA_ESTUDO" "FACADE")
 (cg:rect (list (+ tx (/ (- (- x1 x0) 900) 2.0)) lineY
  (+ tx (/ (+ (- x1 x0) 900) 2.0)) (+ lineY 2100)) "CASA_ESTUDO" "FACADE")
 (princ))
(defun cg:store-model (model / dictionary entry str chunks i record)
 (setq entry (dictsearch (namedobjdict) "CASA_BH_MODELS"))
 (if entry (setq dictionary (cdr (assoc -1 entry)))
  (progn (setq dictionary (entmakex '((0 . "DICTIONARY") (100 . "AcDbDictionary") (281 . 1))))
   (dictadd (namedobjdict) "CASA_BH_MODELS" dictionary)))
 (setq str (cg:json model) chunks nil i 1)
 (while (<= i (strlen str)) (setq chunks (append chunks (list (cons 1 (substr str i 240))))) (setq i (+ i 240)))
 (setq record (entmakex (append '((0 . "XRECORD") (100 . "AcDbXrecord") (280 . 1)) chunks)))
 (if (not (dictadd dictionary (cg:get "project_id" model) record))
  (progn (princ "\nFalha ao gravar snapshot do projeto.") (exit))))
(defun cg:restore-vars (values / pair)
 (foreach pair values (setvar (car pair) (cdr pair))))
(defun cg:commit (model / *error* saved undoStarted ucsChanged key *cg-pid* *cg-drawing-model*)
 (setq saved nil undoStarted nil ucsChanged nil *cg-pid* (cg:get "project_id" model))
 (foreach key '("CMDECHO" "OSMODE" "CLAYER" "DIMTXT" "DIMASZ" "DIMSCALE" "DIMDEC" "DIMLUNIT" "DIMLFAC" "DIMZIN" "DIMPOST" "DIMTAD" "DIMTIH" "DIMTOH" "DIMGAP" "DIMEXE" "DIMEXO" "DIMTSZ")
  (setq saved (cons (cons key (getvar key)) saved)))
 (defun *error* (message)
  (if ucsChanged (command-s "_.UCS" "_Previous"))
  (cg:restore-vars saved)
  (if undoStarted (progn (command-s "_.UNDO" "_End") (command-s "_.U")))
  (princ (strcat "\nGeracao cancelada: " message)) (princ))
 (if (or (/= (getvar "INSUNITS") 4) (/= (getvar "TILEMODE") 1))
  (progn (princ "\nUse a aba Modelo e desenho em milimetros (INSUNITS=4). Nenhuma entidade criada.") nil)
  (progn
   (command-s "_.UNDO" "_Begin") (setq undoStarted T)
   (command-s "_.UCS" "_World") (setq ucsChanged T)
   (regapp "CASA_BH")
   (setvar "CMDECHO" 0) (setvar "OSMODE" 0)
   (setvar "DIMTXT" 140) (setvar "DIMASZ" 120) (setvar "DIMSCALE" 1.0)
   (setvar "DIMDEC" 2) (setvar "DIMLUNIT" 2) (setvar "DIMLFAC" 0.001)
   (setvar "DIMZIN" 0) (setvar "DIMPOST" "<>")
   (setvar "DIMTAD" 1) (setvar "DIMTIH" 0) (setvar "DIMTOH" 0)
   (setvar "DIMGAP" 60) (setvar "DIMEXE" 100) (setvar "DIMEXO" 80) (setvar "DIMTSZ" 70)
   (cg:draw-model model) (cg:store-model model)
   (command-s "_.UCS" "_Previous") (setq ucsChanged nil)
   (cg:restore-vars saved)
   (command-s "_.UNDO" "_End") (setq undoStarted nil)
   (setq *casa-last* model) T)))
(defun c:CASA_GERAR (/ origin model params pid)
 (if (and (cg:ensure-core) (cg:form))
  (progn
   (setq origin (getpoint "\nPonto de insercao do canto frontal esquerdo do lote: "))
   (if origin
    (progn
     (setq origin (trans origin 1 0) pid (strcat "CG-" (rtos (getvar "CDATE") 2 8) "-" (itoa (getvar "MILLISECS"))))
     (setq params (append *casa-params* (list (cons "origin_x" (car origin)) (cons "origin_y" (cadr origin)) (cons "project_id" pid))))
     (setq model (cg:generate params))
     (if (cg:get "error" model) (alert (cg:get "error" model))
      (if (cg:commit model)
       (princ "\nPlanta criada. ZOOM Extents para visualizar. CASA_EXPORTAR envia o snapshot para JSON/Revit.")))))))
 (princ))
(defun cg:stored-json (pid / entry dictionary row result)
 (setq entry (dictsearch (namedobjdict) "CASA_BH_MODELS") result nil)
 (if entry
  (progn (setq dictionary (cdr (assoc -1 entry)) entry (dictsearch dictionary pid))
   (if entry (progn (setq result "") (foreach row entry (if (= (car row) 1) (setq result (strcat result (cdr row))))))))) result)
(defun c:CASA_EXPORTAR (/ selection entity xd pid snapshot file stream)
 (setq selection (entsel "\nSelecione uma entidade da planta gerada (Enter = ultimo projeto nesta sessao): "))
 (if selection
  (progn (setq entity (car selection) xd (assoc -3 (entget entity '("CASA_BH"))))
   (if xd (setq pid (cdr (assoc 1000 (cdr (cadr xd)))))))
  (if *casa-last* (setq pid (cg:get "project_id" *casa-last*))))
 (if pid (setq snapshot (cg:stored-json pid)))
 (if snapshot
  (progn
   (setq file (getfiled "Exportar snapshot gerado - edicoes manuais nao incluidas" (strcat (getvar "DWGPREFIX") pid ".json") "json" 1))
   (if file
    (progn (setq stream (open file "w"))
     (if stream (progn (write-line snapshot stream) (close stream) (princ (strcat "\nJSON salvo: " file)))
      (alert "Nao foi possivel gravar o arquivo.")))))
  (alert "Nenhum snapshot encontrado. Selecione uma entidade CASA_BH gerada neste desenho."))
 (princ))
(defun c:CASA_AJUDA ()
 (alert "CASA_GERAR: formulario e planta. CASA_EXPORTAR: JSON para Dynamo/Revit.\nLeia README.md. Estudo preliminar em lote hipotetico; nao e projeto aprovado.\nEdicoes manuais nao atualizam o JSON. Para outra alternativa, altere a semente e gere em outro ponto.") (princ))
(princ "\nCASA BH carregado. Comandos: CASA_GERAR, CASA_EXPORTAR, CASA_AJUDA.")
(princ)

;;; CASA BH 0.4 - geometry-independent CAD presentation.
(defun cg:circle (p radius layer id)
 (cg:mk (list '(0 . "CIRCLE") (cons 8 layer) (cons 10 (append p '(0.0))) (cons 40 radius)) id))
(defun cd:legacy-furniture (item / b k id x0 x1 y0 y1 w d cx cy p)
 (setq b (cg:get "bounds" item) k (cg:get "kind" item) id (cg:get "id" item)
  x0 (nth 0 b) y0 (nth 1 b) x1 (nth 2 b) y1 (nth 3 b) w (- x1 x0) d (- y1 y0)
  cx (/ (+ x0 x1) 2.0) cy (/ (+ y0 y1) 2.0))
 (cg:rect b "CASA_MOVEIS" id)
 (cond
  ((member k '("bed" "single_bed" "double_bed" "bed_double" "bed_single"))
   (cg:rect (list (+ x0 80) (- y1 480) (- x1 80) (- y1 80)) "CASA_MOVEIS" id)
   (cg:line (list x0 (- y1 600)) (list x1 (- y1 600)) "CASA_MOVEIS" id))
  ((member k '("sofa" "armchair" "loveseat"))
   (cg:rect (list (+ x0 100) (+ y0 100) (- x1 100) (- y1 180)) "CASA_MOVEIS" id)
   (if (> w 1500) (cg:line (list cx (+ y0 100)) (list cx (- y1 180)) "CASA_MOVEIS" id)))
  ((member k '("chair" "desk_chair" "dining_chair" "office_chair"))
   (cg:line (list (+ x0 50) (- y1 100)) (list (- x1 50) (- y1 100)) "CASA_MOVEIS" id))
  ((member k '("sink" "basin" "tank" "laundry_sink"))
   (cg:rect (list (+ x0 100) (+ y0 100) (- x1 100) (- y1 100)) "CASA_MOVEIS" id)
   (cg:circle (list cx cy) 35 "CASA_MOVEIS" id))
  ((= k "toilet") (cg:circle (list cx (+ y0 (* d 0.4))) (* w 0.28) "CASA_MOVEIS" id)
   (cg:rect (list (+ x0 60) (- y1 200) (- x1 60) y1) "CASA_MOVEIS" id))
  ((member k '("stove" "cooktop"))
   (foreach p (list (list (+ x0 (* w 0.28)) (+ y0 (* d 0.28))) (list (+ x0 (* w 0.72)) (+ y0 (* d 0.28)))
    (list (+ x0 (* w 0.28)) (+ y0 (* d 0.72))) (list (+ x0 (* w 0.72)) (+ y0 (* d 0.72))))
    (cg:circle p (* (min w d) 0.12) "CASA_MOVEIS" id)))
  ((= k "washer") (cg:circle (list cx cy) (* (min w d) 0.40) "CASA_MOVEIS" id))
  ((= k "shower") (cg:line (list x0 y0) (list x1 y1) "CASA_MOVEIS" id)
   (cg:circle (list cx cy) 40 "CASA_MOVEIS" id))
  ((member k '("wardrobe" "rack" "tv_console" "tv_rack"))
   (cg:line (list cx y0) (list cx y1) "CASA_MOVEIS" id))
  ((= k "car")
   (cg:rect (list (+ x0 180) (+ y0 (* d 0.22)) (- x1 180) (- y1 (* d 0.22))) "CASA_MOVEIS" id)
   (cg:line (list (+ x0 180) (+ y0 (* d 0.45))) (list (- x1 180) (+ y0 (* d 0.45))) "CASA_MOVEIS" id)
   (cg:line (list (+ x0 180) (- y1 (* d 0.40))) (list (- x1 180) (- y1 (* d 0.40))) "CASA_MOVEIS" id))))

(defun cg:draw-furniture (item / points)
 (if (cg:get "symbol_lines" item)
  (progn
   (cg:rect (cg:get "bounds" item) "CASA_MOVEIS" (cg:get "id" item))
   (foreach points (cg:get "symbol_lines" item) (cd:polyline points nil "CASA_MOVEIS" (cg:get "id" item))))
  (cd:legacy-furniture item)))

(defun cg:draw-opening (o walls / wall c width thick horiz a b id style room box sign tip ang0 ang1)
 (setq wall (cg:find-id (cg:get "wall_id" o) walls) c (cg:get "center" o)
  width (cg:get "width" o) thick (cg:get "thickness" wall) id (cg:get "id" o)
  horiz (equal (cadr (cg:get "start" wall)) (cadr (cg:get "end" wall)) 0.01)
  style (cg:opt "door_style" o "swing"))
 (if horiz
  (setq a (list (- (car c) (/ width 2)) (cadr c)) b (list (+ (car c) (/ width 2)) (cadr c)))
  (setq a (list (car c) (- (cadr c) (/ width 2))) b (list (car c) (+ (cadr c) (/ width 2)))))
 (cond
  ((= (cg:get "kind" o) "window")
   (cg:line a b "CASA_JANELAS" id)
   (if horiz
    (progn (cg:line (list (car a) (+ (cadr a) (/ thick 2))) (list (car b) (+ (cadr b) (/ thick 2))) "CASA_JANELAS" id)
     (cg:line (list (car a) (- (cadr a) (/ thick 2))) (list (car b) (- (cadr b) (/ thick 2))) "CASA_JANELAS" id))
    (progn (cg:line (list (+ (car a) (/ thick 2)) (cadr a)) (list (+ (car b) (/ thick 2)) (cadr b)) "CASA_JANELAS" id)
     (cg:line (list (- (car a) (/ thick 2)) (cadr a)) (list (- (car b) (/ thick 2)) (cadr b)) "CASA_JANELAS" id))))
  ((= style "passage") nil)
  ((= style "sliding") (cg:line a b "CASA_PORTAS" id))
  (T
   (setq room (cg:find-id (cg:get "room_id" o) (cg:get "rooms" *cg-drawing-model*)) box (cg:get "bounds" room))
   (if horiz
    (progn
     (setq sign (if (and box (< (/ (+ (nth 1 box) (nth 3 box)) 2) (cadr c))) -1 1)
      tip (list (car a) (+ (cadr a) (* sign width))))
     (if (= sign 1) (setq ang0 0.0 ang1 (/ pi 2)) (setq ang0 (* 1.5 pi) ang1 (* 2 pi))))
    (progn
     (setq sign (if (and box (< (/ (+ (nth 0 box) (nth 2 box)) 2) (car c))) -1 1)
      tip (list (+ (car a) (* sign width)) (cadr a)))
     (if (= sign 1) (setq ang0 0.0 ang1 (/ pi 2)) (setq ang0 (/ pi 2) ang1 pi))))
   (cg:line a tip "CASA_PORTAS" id)
   (cg:mk (list '(0 . "ARC") '(8 . "CASA_PORTAS") (cons 10 (append a '(0.0)))
    (cons 40 width) (cons 50 ang0) (cons 51 ang1)) id))))

(defun cg:label-box (item / b id txt w h tw th px py cand best score bestscore f fb dims)
 (setq b (cg:get "bounds" item) id (cg:get "id" item) txt (cg:opt "name" item (cg:get "kind" item))
  w (- (nth 2 b) (car b)) h (- (nth 3 b) (cadr b)) tw (min (- w 100) (max 1150 (* 82 (strlen txt)))) th 620 best nil bestscore 1e20)
 (foreach cand '((0.5 0.5) (0.5 0.4) (0.5 0.7) (0.25 0.45) (0.75 0.45) (0.5 0.15) (0.5 0.85))
  (setq px (+ (car b) (* (- w tw) (car cand))) py (+ (cadr b) (* (- h th) (cadr cand)))
   fb (list px py (+ px tw) (+ py th)) score 0)
  (foreach f (cg:get "furniture" *cg-drawing-model*)
   (if (cf:hit fb (cg:get "bounds" f)) (setq score (+ score 1))))
  (foreach f (cf:doors b *cg-drawing-model*) (if (cf:hit fb f) (setq score (+ score 1))))
  (if (< score bestscore) (setq best (list px py) bestscore score)))
 (setq *cj-label-boxes* (cons (list (car best) (cadr best) (+ (car best) tw) (+ (cadr best) th)) *cj-label-boxes*))
 (cg:text (list (car best) (+ (cadr best) 430)) txt 140 "CASA_TEXTOS" id)
 (cg:text (list (car best) (+ (cadr best) 220)) (strcat (rtos (/ (* w h) 1e6) 2 2) " m2") 120 "CASA_TEXTOS" id)
 (cg:text best (strcat (rtos (/ w 1000.0) 2 2) " x " (rtos (/ h 1000.0) 2 2) " m") 110 "CASA_TEXTOS" id))

(defun cg:draw-model (model / site house walls rooms zones item b id x0 y0 x1 y1 tx yy area cutY a z ht wt xs v c width sill nx ny angle endp widthpairs pair dimy sidepos host)
 (setq *cj-label-boxes* nil *cg-drawing-model* model site (cg:get "site_bounds" model) house (cg:get "house_bounds" model)
  walls (cg:get "walls" model) rooms (cg:get "rooms" model) zones (cg:get "zones" model)
  x0 (nth 0 house) y0 (nth 1 house) x1 (nth 2 house) y1 (nth 3 house))
 (foreach item '(("CASA_LOTE" 8) ("CASA_PAREDES" 7) ("CASA_PORTAS" 2) ("CASA_JANELAS" 4)
  ("CASA_MOVEIS" 3) ("CASA_TEXTOS" 7) ("CASA_COTAS" 6) ("CASA_ESTUDO" 8) ("CASA_EXTERNO" 3) ("CASA_COBERTURA" 2) ("CASA_ACESSO" 4))
  (cg:layer (car item) (cadr item)))
 (cg:rect site "CASA_LOTE" "SITE")
 (foreach item (cg:get "outdoor" model) (cg:rect (cg:get "bounds" item) "CASA_EXTERNO" (cg:get "id" item)) (cg:label-box item))
 (if (cg:get "entry_path" model)
  (progn
   (cd:polyline (cg:get "points" (cg:get "entry_path" model)) nil "CASA_ACESSO" "ENTRY-PATH")
   (setq a (car (cg:get "points" (cg:get "entry_path" model))))
   (cg:text (list (+ (car a) 200) (+ (cadr a) 250))
    (strcat "Acesso " (rtos (/ (cg:get "length" (cg:get "entry_path" model)) 1000.0) 2 2) " m") 120 "CASA_TEXTOS" "ENTRY-PATH")))
 (cj:draw model)
 (foreach item (cg:get "openings" model) (cg:draw-opening item walls))
 (foreach item (cg:get "furniture" model) (cg:draw-furniture item))
 (foreach item rooms
  (if (not (member (cg:get "kind" item) '("social" "corridor"))) (cg:label-box item)))
 (foreach item zones
  (setq host (cg:find-id (cg:get "room_id" item) rooms))
  (if (and host (= (cg:get "kind" host) "social")) (cg:label-box item)))
 (cj:dimensions model)
 (setq tx (+ (nth 2 site) 3300) yy (nth 3 site) area 0)
 (cg:text (list tx yy) "CASA BH 0.4 | ESTUDO PRELIMINAR" 280 "CASA_TEXTOS" "TITLE")
 (setq yy (- yy 480))
 (cg:text (list tx yy) (strcat (cg:opt "layout_name" model "Alternativa") " | " (cg:opt "integration_name" model "")) 190 "CASA_TEXTOS" "TITLE")
 (setq yy (- yy 380))
 (cg:text (list tx yy) (strcat "Semente " (itoa (fix (cg:get "seed" model))) " | " (cg:get "project_id" model)) 160 "CASA_TEXTOS" "TITLE")
 (foreach item rooms
  (setq yy (- yy 330) area (+ area (cg:get "net_area_m2" item)))
  (cg:text (list tx yy) (strcat (cg:get "name" item) ": " (rtos (cg:get "net_area_m2" item) 2 2) " m2") 170 "CASA_TEXTOS" "SCHEDULE"))
 (setq yy (- yy 450))
 (cg:text (list tx yy) (strcat "Util " (rtos area 2 2) " m2 | Casa " (rtos (cg:get "gross_area_m2" model) 2 2) " m2") 175 "CASA_TEXTOS" "SCHEDULE")
 (setq yy (- yy 350))
 (cg:text (list tx yy) (strcat "Circulacao: " (rtos (cg:opt "circulation_area_m2" model 0) 2 2) " m2 ("
  (rtos (* 100 (cg:opt "circulation_fraction" model 0)) 2 1) "% da area util)") 160 "CASA_TEXTOS" "METRICS")
 (setq yy (- yy 300))
 (cg:text (list tx yy) (strcat "Janelas: " (itoa (fix (cg:opt "windows_count" model 0))) " | Area geometrica: "
  (rtos (cg:opt "window_area_m2" model 0) 2 2) " m2") 160 "CASA_TEXTOS" "METRICS")
 (foreach item (cg:get "validations" model)
  (setq yy (- yy 300))
  (cg:text (list tx yy) (strcat (cg:get "rule_id" item) ": " (cg:get "status" item)) 150 "CASA_TEXTOS" "CHECK"))
 (foreach item '("Estudo hipotetico. Faixas livres nao sao recuos legais de BH."
   "Cotas em metros. Garagem descoberta. Cobertura conceitual em laje."
   "Conforto: indicadores geometricos; desempenho nao simulado."
   "Revit recebe geracao; edicoes manuais CAD nao sincronizadas.")
  (setq yy (- yy 300)) (cg:text (list tx yy) item 150 "CASA_TEXTOS" "NOTES"))
 ;; North convention: clockwise from +Y, independent of CAD UCS.
 (setq nx (+ (nth 2 site) 1500) ny (- (nth 3 site) 2300)
  angle (* (/ pi 180.0) (cg:opt "north_degrees" model (cg:opt "north" model 0.0)))
  endp (list (+ nx (* 1500 (sin angle))) (+ ny (* 1500 (cos angle)))))
 (cg:line (list nx ny) endp "CASA_ESTUDO" "NORTH")
 (cg:circle endp 90 "CASA_ESTUDO" "NORTH")
 (cg:text (list (+ (car endp) 120) (+ (cadr endp) 120)) "N*" 220 "CASA_TEXTOS" "NORTH")
 (cg:text (list tx (- yy 380)) "* Norte informado; confirmar no levantamento." 150 "CASA_TEXTOS" "NORTH")
 (cd:sections model tx yy)
 (princ))

(defun c:CASA_ALTERNATIVAS (/ origin params model index seed pid ok step)
 (if (and (cg:ensure-core) (cg:form))
  (progn (setq origin (getpoint "\nPonto inicial para comparar tres organizacoes: "))
   (if origin
    (progn (setq origin (trans origin 1 0) index 1 ok 0 seed (fix (cg:get "seed" *casa-params*))
      step (+ (cg:get "lot_width" *casa-params*) 28000))
     (repeat 3
      (setq pid (strcat "CG3-" (itoa (getvar "MILLISECS")) "-" (itoa index))
       params (append (list (cons "layout" index) (cons "seed" seed)
        (cons "origin_x" (+ (car origin) (* (1- index) step))) (cons "origin_y" (cadr origin)) (cons "project_id" pid)) *casa-params*)
       model (cg:generate params))
      (if (cg:get "error" model) (princ (strcat "\nAlternativa " (itoa index) ": " (cg:get "error" model)))
       (if (cg:commit model) (setq ok (1+ ok))))
      (setq index (1+ index)))
     (princ (strcat "\n" (itoa ok) " alternativas desenhadas. CASA_EXPORTAR: selecione a alternativa desejada."))))))
 (princ))
(defun c:CASA_AJUDA ()
 (alert "CASA_GERAR: uma alternativa. CASA_ALTERNATIVAS: compara tres organizacoes.\nCASA_EXPORTAR: snapshot JSON para Revit.\nUse Modelo, INSUNITS=4. Leia LEIA-ME.md.\nRegras municipais e desempenho ambiental ainda pendentes.") (princ))
(princ "\nCASA BH 0.4: CASA_GERAR, CASA_ALTERNATIVAS, CASA_EXPORTAR.") (princ)

(defun ce:raise (message) (princ (strcat "\n" message)) (exit))
;;; CASA BH: persisted furniture dimensions. No executable data in JSON parser.
(defun ce:put (k v obj) (if (assoc k obj) (subst (cons k v) (assoc k obj) obj) (append obj (list (cons k v)))))
(defun cj:space () (while (and (<= cj:i cj:n) (member (ascii (substr cj:s cj:i 1)) '(9 10 13 32))) (setq cj:i (1+ cj:i))))
(defun cj:expect (s) (cj:space) (if (/= (substr cj:s cj:i 1) s) (ce:raise "JSON invalido.")) (setq cj:i (1+ cj:i)))
(defun cj:string (/ out c hex n j code)
 (cj:expect "\"") (setq out "" c "")
 (while (and (<= cj:i cj:n) (/= (setq c (substr cj:s cj:i 1)) "\""))
  (setq cj:i (1+ cj:i))
  (if (= c "\\")
   (progn (setq c (substr cj:s cj:i 1) cj:i (1+ cj:i))
    (cond ((= c "n") (setq c (chr 10))) ((= c "r") (setq c (chr 13))) ((= c "t") (setq c (chr 9)))
     ((= c "b") (setq c (chr 8))) ((= c "f") (setq c (chr 12)))
     ((= c "u") (setq hex (strcase (substr cj:s cj:i 4)) n 0 j 1)
      (repeat 4 (setq code (vl-string-search (substr hex j 1) "0123456789ABCDEF"))
       (if (null code) (ce:raise "Escape JSON invalido.")) (setq n (+ (* n 16) code) j (1+ j)))
      (setq c (chr n) cj:i (+ cj:i 4)))
     ((not (member c '("\"" "\\" "/"))) (ce:raise "Escape JSON invalido.")))))
  (setq out (strcat out c)))
 (cj:expect "\"") out)
(defun cj:value (/ c out key start token val)
 (cj:space) (setq c (substr cj:s cj:i 1))
 (cond ((= c "\"") (cj:string))
  ((member c '("[" "{"))
   (setq cj:i (1+ cj:i) out nil) (cj:space)
   (if (/= (substr cj:s cj:i 1) (if (= c "[") "]" "}"))
    (progn
     (if (= c "{") (progn (setq key (cj:string)) (cj:expect ":") (setq val (cons key (cj:value)))) (setq val (cj:value)))
     (setq out (list val)) (cj:space)
     (while (= (substr cj:s cj:i 1) ",")
      (setq cj:i (1+ cj:i))
      (if (= c "{") (progn (setq key (cj:string)) (cj:expect ":") (setq val (cons key (cj:value)))) (setq val (cj:value)))
      (setq out (cons val out)) (cj:space))))
   (cj:expect (if (= c "[") "]" "}")) (reverse out))
  (T (setq start cj:i)
   (while (and (<= cj:i cj:n) (not (member (substr cj:s cj:i 1) '(" " "\t" "\r" "\n" "," "]" "}")))) (setq cj:i (1+ cj:i)))
   (setq token (substr cj:s start (- cj:i start)))
   (cond ((= token "true") 'cj:true) ((= token "false") 'cj:false) ((= token "null") 'cj:null)
    ((and (> (strlen token) 0) (not (wcmatch token "*[~0-9.eE+-]*")) (setq val (distof token 2))) val)
    (T (ce:raise "Numero JSON invalido."))))))
(defun cj:parse (text / cj:s cj:i cj:n val)
 (setq cj:s text cj:i 1 cj:n (strlen text) val (cj:value)) (cj:space)
 (if (<= cj:i cj:n) (ce:raise "Conteudo apos JSON.")) val)
(defun ce:identity (entity / xd)
 (setq xd (cdr (cadr (assoc -3 (entget entity '("CASA_BH"))))))
 (if (and xd (= (caar xd) 1000) (= (car (cadr xd)) 1000)) (list (cdar xd) (cdr (cadr xd)))))
(defun ce:entities (pid id / ss i out en)
 (setq ss (ssget "_X" '((-3 ("CASA_BH")))) i 0 out nil)
 (if ss (repeat (sslength ss) (setq en (ssname ss i) i (1+ i))
  (if (equal (ce:identity en) (list pid id)) (setq out (cons en out))))) out)
(defun ce:save (model / dict rec data str chunks i fresh pid)
 (setq dict (cdr (assoc -1 (dictsearch (namedobjdict) "CASA_BH_MODELS")))
  rec (dictsearch dict (cg:get "project_id" model)))
 (if (not rec) (ce:raise "Snapshot do projeto ausente."))
 (setq data (vl-remove-if '(lambda (p) (= (car p) 1)) (entget (cdr (assoc -1 rec)))) str (cg:json model) chunks nil i 1)
 (while (<= i (strlen str)) (setq chunks (cons (cons 1 (substr str i 240)) chunks) i (+ i 240)))
 ;; XRECORD entmod appends payload in AutoCAD 2027. Replace the owned record
 ;; inside the same UNDO group, rather than concatenating two JSON documents.
 (setq pid (cg:get "project_id" model)
  fresh (entmakex (append '((0 . "XRECORD") (100 . "AcDbXrecord") (280 . 1)) (reverse chunks))))
 (if (not fresh) (ce:raise "Falha ao criar snapshot."))
 (if (not (dictremove dict pid)) (ce:raise "Falha ao liberar snapshot anterior."))
 (if (not (dictadd dict pid fresh)) (ce:raise "Falha ao registrar snapshot atualizado."))
 (if (entget (cdr (assoc -1 rec))) (entdel (cdr (assoc -1 rec)))))
(defun ce:point (p old new)
 (list (+ (car new) (* (- (car p) (car old)) (/ (- (nth 2 new) (car new)) (- (nth 2 old) (car old)))))
       (+ (cadr new) (* (- (cadr p) (cadr old)) (/ (- (nth 3 new) (cadr new)) (- (nth 3 old) (cadr old)))))))
(defun ce:resize (item width depth height / old new use dx dy angle lines result original ln)
 (setq old (cg:get "bounds" item) angle (cg:opt "rotation" item 0) original (cg:opt "source_bounds_before_edit" item old))
 (if (member angle '(90 270)) (setq dx depth dy width) (setq dx width dy depth))
 (if (or (< dx (max 250 (* 0.65 (- (nth 2 original) (car original)))) )
         (< dy (max 250 (* 0.65 (- (nth 3 original) (cadr original)))) ) (< height 100) (> height 3000))
  (ce:raise "Medidas fora da faixa do modelo: minimo 65% da base/250 mm; altura 100 a 3000 mm."))
 (setq new (list (- (/ (+ (car old) (nth 2 old)) 2.0) (/ dx 2.0)) (- (/ (+ (cadr old) (nth 3 old)) 2.0) (/ dy 2.0))
                 (+ (/ (+ (car old) (nth 2 old)) 2.0) (/ dx 2.0)) (+ (/ (+ (cadr old) (nth 3 old)) 2.0) (/ dy 2.0)))
  use (cg:opt "use_bounds" item old) lines nil)
 (foreach ln (cg:get "symbol_lines" item) (setq lines (cons (mapcar '(lambda (p) (ce:point p old new)) ln) lines)))
 (setq result (ce:put "bounds" new item) result (ce:put "height" height result)
  result (ce:put "use_bounds" (mapcar '+ new (mapcar '- use old)) result)
  result (ce:put "symbol_lines" (reverse lines) result)
  result (ce:put "source_bounds_before_edit" original result)
  result (ce:put "dimension_revision" (1+ (cg:opt "dimension_revision" item 0)) result)) result)
(defun ce:validate (item model / host box others reason f door)
 (setq host (cg:find-id (cg:get "room_id" item) (append (cg:get "rooms" model) (cg:get "outdoor" model)))
  box (if host (cg:get "bounds" host)) reason nil)
 (cond ((not box) (setq reason "Ambiente do movel nao identificado."))
  ((not (and (cf:inside (cg:get "bounds" item) box) (cf:inside (cg:get "use_bounds" item) box))) (setq reason "Movel ou faixa de uso invade a parede/limite do ambiente.")))
 (foreach f (cg:get "furniture" model)
  (if (/= (cg:get "id" f) (cg:get "id" item))
   (if (or (cf:hit (cg:get "bounds" item) (cg:get "bounds" f))
      (and (not (and (member (cg:get "kind" item) '("bed_double" "bed_single")) (= (cg:get "kind" f) "nightstand"))) (cf:hit (cg:get "use_bounds" item) (cg:get "bounds" f)))
      (and (not (and (member (cg:get "kind" f) '("bed_double" "bed_single")) (= (cg:get "kind" item) "nightstand"))) (cf:hit (cg:get "use_bounds" f) (cg:get "bounds" item))))
    (setq reason (strcat "Conflito com movel/faixa de uso: " (cg:get "id" f))))))
 (if box (foreach door (cf:doors box model) (if (cf:hit (cg:get "bounds" item) door) (setq reason "Conflito com abertura de porta."))))
 (if (not (cf:window-clear (list item) model)) (setq reason "Altura/posicao bloqueia janela."))
 (if (> (cg:get "height" item) (cg:get "height" (car (cg:get "walls" model)))) (setq reason "Movel acima do pe-direito.")) reason)
(defun ce:apply (model item / *error* undoStarted entities en old b poly *cg-pid* *cg-drawing-model* newmodel)
 (setq *cg-pid* (cg:get "project_id" model) *cg-drawing-model* model undoStarted nil
  entities (ce:entities *cg-pid* (cg:get "id" item)) old (cg:find-id (cg:get "id" item) (cg:get "furniture" model)) b (cg:get "bounds" old))
 (defun *error* (message)
  (if undoStarted (progn (command-s "_.UNDO" "_End") (command-s "_.U"))) (princ (strcat "\nEdicao cancelada: " message)) (princ))
 (if (not entities) (ce:raise "Geometria do movel ausente."))
 ;; Outline signature detects moved/scaled outlines before regenerating symbols.
 (setq poly nil)
 (foreach en entities
  (if (= (cdr (assoc 0 (entget en))) "LWPOLYLINE")
   (if (equal (mapcar 'cdr (vl-remove-if-not '(lambda (p) (= (car p) 10)) (entget en)))
     (list (list (car b) (cadr b)) (list (nth 2 b) (cadr b)) (list (nth 2 b) (nth 3 b)) (list (car b) (nth 3 b))) 0.1) (setq poly T)))
  (if (= 4 (logand 4 (cdr (assoc 70 (tblsearch "LAYER" (cdr (assoc 8 (entget en)))))))) (ce:raise "Camada de movel bloqueada.")))
 (if (not poly) (ce:raise "Contorno alterado manualmente. Desfaca MOVE/SCALE antes de editar parametros."))
 (setq newmodel (ce:put "furniture" (mapcar '(lambda (f) (if (= (cg:get "id" f) (cg:get "id" item)) item f)) (cg:get "furniture" model)) model))
 (command-s "_.UNDO" "_Begin") (setq undoStarted T)
 (foreach en entities (if (not (entdel en)) (ce:raise "Falha ao remover simbolo anterior.")))
 (cg:draw-furniture item) (ce:save newmodel)
 (command-s "_.UNDO" "_End") (setq undoStarted nil *casa-last* newmodel) newmodel)
(defun c:CASA_MOVEL_EDITAR (/ *error* selection ids model item b width depth height changed reason)
 (defun *error* (message) (princ (strcat "\nEdicao cancelada: " message)) (princ))
 (setq selection (entsel "\nSelecione uma linha do movel CASA: "))
 (if selection
  (progn
   (setq ids (ce:identity (car selection))) (if (not ids) (ce:raise "Selecione um movel gerado pelo CASA."))
   (setq model (cj:parse (cg:stored-json (car ids))) item (cg:find-id (cadr ids) (cg:get "furniture" model)))
   (if (not item) (ce:raise "Entidade nao e movel do projeto."))
   (setq b (cg:get "bounds" item) width (- (nth 2 b) (car b)) depth (- (nth 3 b) (cadr b)) height (cg:get "height" item))
   (if (member (cg:opt "rotation" item 0) '(90 270)) (setq width (- (nth 3 b) (cadr b)) depth (- (nth 2 b) (car b))))
   (princ (strcat "\n" (cg:get "id" item) " | " (cg:get "kind" item) " | Medidas locais em METROS. Centro e orientacao preservados."))
   (initget 6) (setq width (* 1000 (cond ((getreal (strcat "\nLargura <" (rtos (/ width 1000.0) 2 3) ">: "))) (T (/ width 1000.0)))))
   (initget 6) (setq depth (* 1000 (cond ((getreal (strcat "\nProfundidade <" (rtos (/ depth 1000.0) 2 3) ">: "))) (T (/ depth 1000.0)))))
   (initget 6) (setq height (* 1000 (cond ((getreal (strcat "\nAltura <" (rtos (/ height 1000.0) 2 3) ">: "))) (T (/ height 1000.0)))))
   (setq changed (ce:resize item width depth height) reason (ce:validate changed model))
   (if reason (ce:raise reason))
   (if (ce:apply model changed) (princ "\nMovel e snapshot atualizados. Salve o DWG e use CASA_EXPORTAR para enviar as medidas ao Revit.")))) (princ))
(princ "\nCASA_MOVEL_EDITAR: dimensoes de moveis em metros, com exportacao para Revit.") (princ)
