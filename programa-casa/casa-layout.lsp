;;; CASA BH 0.4. Articulated architectural organizations, millimetres.
;;; Geometric design targets only: no legal or thermal compliance implied.
(defun cl:area (b) (/ (* (- (nth 2 b) (nth 0 b)) (- (nth 3 b) (nth 1 b))) 1000000.0))
(defun cl:spec (kind name depth) (list (cons "kind" kind) (cons "name" name) (cons "depth" depth)))
(defun cl:room (spec axes / id b)
  (setq id (strcat "R" (itoa (1+ (length *cl-rooms*)))))
  (setq b (list (+ (nth 0 axes) (/ (if (equal (nth 0 axes) *cl-xa* 0.01) *cl-te* *cl-ti*) 2.0))
    (+ (nth 1 axes) (/ (if (equal (nth 1 axes) *cl-ya* 0.01) *cl-te* *cl-ti*) 2.0))
    (- (nth 2 axes) (/ (if (equal (nth 2 axes) *cl-xb* 0.01) *cl-te* *cl-ti*) 2.0))
    (- (nth 3 axes) (/ (if (equal (nth 3 axes) *cl-yb* 0.01) *cl-te* *cl-ti*) 2.0))))
  (setq *cl-rooms* (append *cl-rooms* (list (list (cons "id" id) (cons "kind" (cg:get "kind" spec))
    (cons "name" (cg:get "name" spec)) (cons "axes" axes) (cons "bounds" b) (cons "net_area_m2" (cl:area b)))))) id)
(defun cl:zone (kind name box room)
  (setq *cl-zones* (append *cl-zones* (list (list (cons "id" (strcat "Z" (itoa (1+ (length *cl-zones*)))))
    (cons "room_id" room) (cons "kind" kind) (cons "name" name) (cons "bounds" box) (cons "net_area_m2" (cl:area box)))))))
(defun cl:split (items / a b it sa sb)
  (setq sa 0.0 sb 0.0)
  (foreach it items (if (<= sa sb) (setq a (append a (list it)) sa (+ sa (cg:get "depth" it)))
    (setq b (append b (list it)) sb (+ sb (cg:get "depth" it)))))
  (list a b))
(defun cl:sumdepth (items / total it)
  (setq total 0.0) (foreach it items (setq total (+ total (cg:get "depth" it) *cl-ti*))) total)
(defun cl:depth-insert (item items)
  (cond ((not items) (list item))
    ((> (cg:get "depth" item) (cg:get "depth" (car items))) (cons item items))
    (T (cons (car items) (cl:depth-insert item (cdr items))))))
(defun cl:depth-sort (items / sorted item)
  (foreach item items (setq sorted (cl:depth-insert item sorted))) sorted)
(defun cl:section-depth (items lateral / parts)
  (setq parts (cl:split items)) (max (cl:sumdepth (car parts)) (cl:sumdepth (cadr parts))))
(defun cl:strip (items xlo xhi ya yb / cursor total extra spec dep largest)
  (setq cursor ya total (cl:sumdepth items) extra (- (- yb ya) total) largest (car items))
  (foreach spec items (if (> (cg:get "depth" spec) (cg:get "depth" largest)) (setq largest spec)))
  (foreach spec items
    (setq dep (+ (cg:get "depth" spec) *cl-ti* (if (equal spec largest) extra 0)))
    (cl:room spec (list xlo cursor xhi (+ cursor dep))) (setq cursor (+ cursor dep))))
(defun cl:section (items ya yb lateral / ca cb parts split)
  (progn
      (setq split (if lateral (+ 0.405 (* 0.025 (cg:rand))) (+ 0.46 (* 0.08 (cg:rand))))
        ca (+ *cl-xa* (* split (- (- *cl-xb* *cl-xa*) *cl-cw* *cl-ti*))) cb (+ ca *cl-cw* *cl-ti*)
        parts (cl:split items))
      (cl:strip (car parts) *cl-xa* ca ya yb) (cl:strip (cadr parts) cb *cl-xb* ya yb))
  (cl:room (cl:spec "corridor" "Circulacao" 0) (list ca ya cb yb)))
(defun cl:social (ya yb integration dining / room a b usable wl wd wk cursor specs spec rid axes bounds)
  (setq a (+ *cl-xa* (/ *cl-te* 2.0)) b (- *cl-xb* (/ *cl-te* 2.0)) usable (- b a)
    wl (if (= dining 1) 3000.0 (* usable 0.60)) wd (if (= dining 1) 2700.0 0.0)
    wk (- usable wl wd (cond ((= integration 3) (* (if (= dining 1) 2 1) *cl-ti*)) ((= integration 2) *cl-ti*) (T 0.0))))
  (setq specs (list (list "living" "Sala" wl)))
  (if (= dining 1) (setq specs (append specs (list (list "dining" "Jantar" wd)))))
  (setq specs (append specs (list (list "kitchen" "Cozinha" wk))))
  (cond
    ((= integration 1)
      (setq rid (cl:room (cl:spec "social" "Convivencia integrada" 0) (list *cl-xa* ya *cl-xb* yb)) cursor a)
      (foreach spec specs
        (cl:zone (car spec) (cadr spec) (list cursor (+ ya (/ (if (equal ya *cl-ya* 0.01) *cl-te* *cl-ti*) 2.0))
          (+ cursor (nth 2 spec)) (- yb (/ (if (equal yb *cl-yb* 0.01) *cl-te* *cl-ti*) 2.0))) rid)
        (setq cursor (+ cursor (nth 2 spec)))))
    ((= integration 2)
      (setq cursor (+ a wl wd (/ *cl-ti* 2.0)) rid (cl:room (cl:spec "social" (if (= dining 1) "Sala e jantar" "Sala") 0) (list *cl-xa* ya cursor yb)))
      (setq bounds (cg:get "bounds" (last *cl-rooms*)))
      (cl:zone "living" "Sala" (list a (nth 1 bounds) (+ a wl) (nth 3 bounds)) rid)
      (if (= dining 1) (cl:zone "dining" "Jantar" (list (+ a wl) (nth 1 bounds) (+ a wl wd) (nth 3 bounds)) rid))
      (cl:room (cl:spec "kitchen" "Cozinha" 0) (list cursor ya *cl-xb* yb)))
    (T
      (setq cursor *cl-xa*)
      (foreach spec specs
        (setq b (if (= (car spec) "kitchen") *cl-xb* (+ cursor (nth 2 spec) (if (equal cursor *cl-xa* 0.01) (/ (+ *cl-te* *cl-ti*) 2.0) *cl-ti*))))
        (cl:room (cl:spec (car spec) (cadr spec) 0) (list cursor ya b yb)) (setq cursor b)))))
(defun cl:recess-size (room / bounds)
  (setq bounds (cg:get "bounds" room))
  (min (if (member (cg:get "kind" room) '("bathroom" "laundry")) 1400 800)
    (- (nth 2 bounds) (car bounds) (if (member (cg:get "kind" room) '("bathroom" "laundry")) 2400 3300))))
(defun cl:articulate (frontside / room candidate axes bounds shift cut x y best leftside)
  ;; Choose the corner that offers the largest functional recess, including service rooms.
  (setq best -1)
  (foreach room *cl-rooms*
    (setq axes (cg:get "axes" room))
    (if (and (or (equal (car axes) *cl-xa* 0.01) (equal (nth 2 axes) *cl-xb* 0.01))
        (equal (if frontside (cadr axes) (nth 3 axes)) (if frontside *cl-ya* *cl-yb*) 0.01)
        (not (cl:social-p (cg:get "kind" room))) (> (cl:recess-size room) best))
      (setq candidate room best (cl:recess-size room))))
  (if (and candidate (> best 100))
    (progn
      (setq axes (cg:get "axes" candidate) bounds (cg:get "bounds" candidate) shift (* best (cg:opt "_recess_scale" params 1.0)) leftside (equal (car axes) *cl-xa* 0.01)
        axes (if leftside (cons (+ (car axes) shift) (cdr axes)) (list (car axes) (cadr axes) (- (nth 2 axes) shift) (nth 3 axes)))
        bounds (if leftside (cons (+ (car bounds) shift) (cdr bounds)) (list (car bounds) (cadr bounds) (- (nth 2 bounds) shift) (nth 3 bounds)))
        *cl-rooms* (subst (subst (cons "net_area_m2" (cl:area bounds)) (assoc "net_area_m2" candidate)
          (subst (cons "bounds" bounds) (assoc "bounds" candidate)
            (subst (cons "axes" axes) (assoc "axes" candidate) candidate))) candidate *cl-rooms*)
        x (if leftside (+ x0 shift) (- x1 shift))
        y (+ (if frontside (nth 3 axes) (cadr axes)) (if frontside (- (/ *cl-te* 2.0)) (/ *cl-te* 2.0))))
      (setq *cl-footprint*
        (if leftside
          (if frontside
            (list (list x y0) (list x1 y0) (list x1 ye) (list x0 ye) (list x0 y) (list x y))
            (list (list x0 y0) (list x1 y0) (list x1 ye) (list x ye) (list x y) (list x0 y)))
          (if frontside
            (list (list x0 y0) (list x y0) (list x y) (list x1 y) (list x1 ye) (list x0 ye))
            (list (list x0 y0) (list x1 y0) (list x1 y) (list x y) (list x ye) (list x0 ye))))))))
(defun cl:polygon-area (points / total a b seq)
  (setq total 0.0 seq (append points (list (car points))))
  (while (cdr seq) (setq a (car seq) b (cadr seq) total (+ total (- (* (car a) (cadr b)) (* (car b) (cadr a)))) seq (cdr seq)))
  (/ (abs total) 2000000.0))
(defun cl:edges (room / b id)
  (setq b (cg:get "axes" room) id (cg:get "id" room))
  (list (list "H" (nth 1 b) (nth 0 b) (nth 2 b) id) (list "H" (nth 3 b) (nth 0 b) (nth 2 b) id)
    (list "V" (nth 0 b) (nth 1 b) (nth 3 b) id) (list "V" (nth 2 b) (nth 1 b) (nth 3 b) id)))
(defun cl:unique-sort (vals / out val)
  (foreach val (vl-sort vals '<) (if (or (not out) (not (equal val (car out) 0.01))) (setq out (cons val out)))) (reverse out))
(defun cl:build-walls (/ edges room edge other cuts v starts end mid owners a b thick id wall)
  (foreach room *cl-rooms* (setq edges (append edges (cl:edges room))))
  (foreach edge edges
    (setq cuts (list (nth 2 edge) (nth 3 edge)))
    (foreach other edges
      (if (and (= (car edge) (car other)) (equal (cadr edge) (cadr other) 0.01))
        (foreach v (list (nth 2 other) (nth 3 other)) (if (and (> v (nth 2 edge)) (< v (nth 3 edge))) (setq cuts (cons v cuts))))))
    (setq cuts (cl:unique-sort cuts))
    (while (cdr cuts)
      (setq starts (car cuts) end (cadr cuts) mid (/ (+ starts end) 2.0) owners nil)
      (foreach other edges
        (if (and (= (car edge) (car other)) (equal (cadr edge) (cadr other) 0.01) (> mid (nth 2 other)) (< mid (nth 3 other)))
          (setq owners (cons (nth 4 other) owners))))
      (setq *cg-wall-role* (if (= (length owners) 1) "external" "internal") thick (if (= *cg-wall-role* "external") *cl-te* *cl-ti*)
        a (if (= (car edge) "H") (list starts (cadr edge)) (list (cadr edge) starts))
        b (if (= (car edge) "H") (list end (cadr edge)) (list (cadr edge) end))
        id (cg:add-wall a b thick *cl-height*))
      (setq wall (car (vl-remove-if-not '(lambda (w) (= (cg:get "id" w) id)) *cg-walls*)))
      (if (not (assoc "room_ids" wall)) (setq *cg-walls* (subst (append wall (list (cons "room_ids" owners))) wall *cg-walls*)))
      (setq cuts (cdr cuts)))))
(defun cl:remeasure (/ room axes b wall a c side zone host zb)
  (foreach room *cl-rooms*
    (setq axes (cg:get "axes" room) b (list (+ (car axes) (/ *cl-ti* 2.0)) (+ (cadr axes) (/ *cl-ti* 2.0)) (- (nth 2 axes) (/ *cl-ti* 2.0)) (- (nth 3 axes) (/ *cl-ti* 2.0))))
    (foreach wall *cg-walls*
      (if (and (= (length (cg:get "room_ids" wall)) 1) (member (cg:get "id" room) (cg:get "room_ids" wall)))
        (progn (setq a (cg:get "start" wall) c (cg:get "end" wall))
          (cond
            ((and (equal (car a) (car c) 0.01) (equal (car a) (car axes) 0.01)) (setq b (list (+ (car axes) (/ *cl-te* 2.0)) (cadr b) (nth 2 b) (nth 3 b))))
            ((equal (car a) (car c) 0.01) (setq b (list (car b) (cadr b) (- (nth 2 axes) (/ *cl-te* 2.0)) (nth 3 b))))
            ((equal (cadr a) (cadr axes) 0.01) (setq b (list (car b) (+ (cadr axes) (/ *cl-te* 2.0)) (nth 2 b) (nth 3 b))))
            (T (setq b (list (car b) (cadr b) (nth 2 b) (- (nth 3 axes) (/ *cl-te* 2.0)))))))))
    (setq *cl-rooms* (subst (subst (cons "net_area_m2" (cl:area b)) (assoc "net_area_m2" room) (subst (cons "bounds" b) (assoc "bounds" room) room)) room *cl-rooms*)))
  (foreach zone *cl-zones*
    (setq host (cl:room-by-id (cg:get "room_id" zone)) b (cg:get "bounds" host) zb (cg:get "bounds" zone)
      zb (list (max (car b) (car zb)) (max (cadr b) (cadr zb)) (min (nth 2 b) (nth 2 zb)) (min (nth 3 b) (nth 3 zb))))
    (setq *cl-zones* (subst (subst (cons "net_area_m2" (cl:area zb)) (assoc "net_area_m2" zone) (subst (cons "bounds" zb) (assoc "bounds" zone) zone)) zone *cl-zones*))))
(defun cl:room-by-id (id) (car (vl-remove-if-not '(lambda (r) (= (cg:get "id" r) id)) *cl-rooms*)))
(defun cl:social-p (kind) (member kind '("social" "living" "dining" "kitchen")))
(defun cl:length (wall) (distance (cg:get "start" wall) (cg:get "end" wall)))
(defun cl:door (wall room other width style / a b center opening)
  (setq a (cg:get "start" wall) b (cg:get "end" wall) center (mapcar '(lambda (u v) (/ (+ u v) 2.0)) a b))
  (if (and other (cl:social-p (cg:get "kind" (cl:room-by-id room))) (cl:social-p (cg:get "kind" (cl:room-by-id other)))
      (equal (car a) (car b) 0.01)) (setq center (list (car a) (+ (cadr a) 700))))
  (cg:add-opening (cg:get "id" wall) "door" center width 2100 0 room)
  (setq opening (last *cg-openings*))
  (setq *cg-openings* (subst (append opening (list (cons "door_style" style) (cons "connected_room_id" (if other other "EXTERIOR")))) opening *cg-openings*)))
(defun cl:openings (/ wall owners r1 r2 k1 k2 room best candidate win a b width entry bestlen zone entrance opening entrancex)
  ;; Every private room opens to a corridor; social rooms connect to each other.
  (foreach wall *cg-walls*
    (setq owners (cg:get "room_ids" wall))
    (if (= (length owners) 2)
      (progn (setq r1 (cl:room-by-id (car owners)) r2 (cl:room-by-id (cadr owners)) k1 (cg:get "kind" r1) k2 (cg:get "kind" r2))
        (if (and (> (cl:length wall) 1050)
          (or (= k1 "corridor") (= k2 "corridor") (and (cl:social-p k1) (cl:social-p k2))))
          (cl:door wall (if (= k1 "corridor") (cg:get "id" r2) (cg:get "id" r1))
            (if (= k1 "corridor") (cg:get "id" r1) (cg:get "id" r2))
            (if (or (= k1 "corridor") (= k2 "corridor")) 900 1000)
            (if (and (cl:social-p k1) (cl:social-p k2) (= integration 3)) "sliding"
              (if (and (or (cl:social-p k1) (= k1 "corridor")) (or (cl:social-p k2) (= k2 "corridor"))) "passage" "hinged")))))))
  ;; Principal arrival always on the front, including a distribution hall/corridor.
  (setq entry nil bestlen -1)
  (foreach wall *cg-walls*
    (setq owners (cg:get "room_ids" wall))
    (if (and (= (length owners) 1) (or (cl:social-p (cg:get "kind" (cl:room-by-id (car owners)))) (= (cg:get "kind" (cl:room-by-id (car owners))) "corridor")) (> (cl:length wall) 1050)
        (equal (cadr (cg:get "start" wall)) *cl-ya* 0.01) (equal (cadr (cg:get "end" wall)) *cl-ya* 0.01))
      (progn
        (setq a (cg:get "start" wall) b (cg:get "end" wall)
          candidate (+ (cl:length wall) (if (and (equal (cadr a) *cl-ya* 0.01) (equal (cadr b) *cl-ya* 0.01)) 100000 0)))
        (if (> candidate bestlen) (setq bestlen candidate entry wall)))))
  (if entry (progn (cl:door entry (car (cg:get "room_ids" entry)) nil 1000 "hinged")
    (setq opening (last *cg-openings*))
    (foreach zone *cl-zones*
      (if (and (= (cg:get "room_id" zone) (cg:get "room_id" opening)) (= (cg:get "kind" zone) "living"))
        (progn (setq entrance (cg:get "bounds" zone) entrancex (/ (+ (car entrance) (nth 2 entrance)) 2.0))
          (setq *cg-openings* (subst (subst (cons "center" (list entrancex *cl-ya*)) (assoc "center" opening) opening) opening *cg-openings*)))))
    (setq *cl-main-entry* (cg:get "id" (last *cg-openings*)) *cl-entry-center* (cg:get "center" (last *cg-openings*)))))
  ;; Windows on each functional zone, unless the same external segment carries the entry.
  (foreach room *cl-rooms*
    (if (/= (cg:get "kind" room) "corridor")
      (progn (setq best nil bestlen 0)
        (foreach wall *cg-walls*
          (if (and (= (length (cg:get "room_ids" wall)) 1) (member (cg:get "id" room) (cg:get "room_ids" wall))
              (not (equal wall entry)) (> (cl:length wall) bestlen)) (setq best wall bestlen (cl:length wall))))
        (if best
          (progn (setq a (cg:get "start" best) b (cg:get "end" best) width (min (- bestlen 400) (if (= (cg:get "kind" room) "bathroom") 800 1600)))
            (if (> width 500) (cg:add-opening (cg:get "id" best) "window" (mapcar '(lambda (u v) (/ (+ u v) 2.0)) a b)
              width (if (= (cg:get "kind" room) "bathroom") 600 1200) (if (= (cg:get "kind" room) "bathroom") 1600 1000) (cg:get "id" room)))))))))
(defun cl:zone-windows (/ zone box wall a b owners lo hi mid vertical width center conflict opening)
  ;; More than one window is allowed on a host; functional social zones receive their own apertures.
  (foreach zone *cl-zones*
    (setq box (cg:get "bounds" zone))
    (foreach wall *cg-walls*
      (setq owners (cg:get "room_ids" wall))
      (if (and (= (length owners) 1) (member (cg:get "room_id" zone) owners))
        (progn
          (setq a (cg:get "start" wall) b (cg:get "end" wall) vertical (equal (car a) (car b) 0.01)
            lo (max (if vertical (cadr a) (car a)) (if vertical (cadr box) (car box)))
            hi (min (if vertical (cadr b) (car b)) (if vertical (nth 3 box) (nth 2 box))))
          (if (and (> (- hi lo) 1300)
              (if vertical (or (< (abs (- (car a) (car box))) 160) (< (abs (- (car a) (nth 2 box))) 160))
                (or (< (abs (- (cadr a) (cadr box))) 160) (< (abs (- (cadr a) (nth 3 box))) 160))))
            (progn
              (setq mid (/ (+ lo hi) 2.0) width (if (= (cg:get "kind" zone) "bathroom") 800 (min 1500 (- hi lo 400)))
                center (if vertical (list (car a) mid) (list mid (cadr a))) conflict nil)
              (foreach opening *cg-openings*
                (if (and (= (cg:get "wall_id" opening) (cg:get "id" wall))
                    (< (distance center (cg:get "center" opening)) (+ 150 (/ (+ width (cg:get "width" opening)) 2.0)))) (setq conflict T)))
              (if (not conflict) (cg:add-opening (cg:get "id" wall) "window" center width
                (if (= (cg:get "kind" zone) "bathroom") 600 1200) (if (= (cg:get "kind" zone) "bathroom") 1600 1000) (cg:get "room_id" zone))))))))))
(defun cl:reachable (/ reached changed opening a b room missing)
  (setq reached '("EXTERIOR") changed T)
  (while changed
    (setq changed nil)
    (foreach opening *cg-openings*
      (if (= (cg:get "kind" opening) "door")
        (progn (setq a (cg:get "room_id" opening) b (cg:get "connected_room_id" opening))
          (cond ((and (member a reached) (not (member b reached))) (setq reached (cons b reached) changed T))
            ((and (member b reached) (not (member a reached))) (setq reached (cons a reached) changed T)))))))
  (foreach room *cl-rooms* (if (not (member (cg:get "id" room) reached)) (setq missing T))) (not missing))
(defun cl:generate-candidate (params / err *cg-walls* *cg-openings* *cg-furniture* *cg-seed* *cg-wall-role*
    *cl-footprint* *cl-main-entry* *cl-entry-center* *cl-rooms* *cl-zones* *cl-ti* *cl-te* *cl-height* *cl-cw* *cl-xa* *cl-xb* *cl-ya* *cl-yb*
    specs spec idx program layout integration parking occupants north ox oy x0 x1 y0 ye front
    nfirst groupa groupb item da db socialdepth socialya socialyb total room model outdoor garagewidth rearspace checks circarea netarea winarea wincount gx gy pathstart pathcorner entrypath)
  (setq err (cg:validate-input params))
  (foreach spec '(("parking" 0 2 1) ("occupants" 1 6 4) ("layout" 0 3 0) ("integration" 0 3 0) ("terrace" 0 1 1))
    (setq item (cg:opt (car spec) params (nth 3 spec)))
    (if (or (not (numberp item)) (< item (cadr spec)) (> item (nth 2 spec)) (/= item (fix item))) (setq err (strcat "Campo invalido: " (car spec)))))
  (setq north (cg:opt "north" params 0))
  (if (or (not (numberp north)) (< north 0) (>= north 360)) (setq err "Norte deve estar entre 0 e 359.99 graus."))
  (if (and (not err) (or (> (cg:get "living" params) 1) (> (cg:get "kitchens" params) 1) (> (cg:get "dining" params) 1)))
    (setq err "Versao 0.3 aceita uma sala, uma cozinha e ate um jantar; multiplos setores sociais ainda nao implementados."))
  (if (and (not err) (> (cg:opt "occupants" params 4) (* 2 (cg:get "bedrooms" params)))) (setq err "Moradores excedem capacidade de duas pessoas por quarto."))
  (if err (list (cons "error" err))
    (progn
      (setq *cg-seed* (cg:get "seed" params) *cl-ti* (cg:wall-thickness "wall_internal" params) *cl-te* (cg:wall-thickness "wall_external" params)
        *cl-height* (cg:get "height" params) *cl-cw* (cg:get "corridor" params) parking (fix (cg:opt "parking" params 1))
        occupants (fix (cg:opt "occupants" params 4)) layout (fix (cg:opt "layout" params 0)) integration (fix (cg:opt "integration" params 0))
        ox (cg:opt "origin_x" params 0) oy (cg:opt "origin_y" params 0))
      ;; Advance the seed before categorical selection: nearby seeds must differ too.
      (repeat 4 (cg:rand))
      (if (= layout 0) (setq layout (1+ (fix (* 3 (cg:rand))))))
      (if (= integration 0) (setq integration (1+ (fix (* 3 (cg:rand))))))
      (foreach spec '(("bedrooms" "bedroom" "Quarto" 3400) ("bathrooms" "bathroom" "Banheiro" 2300)
          ("laundry" "laundry" "Lavanderia" 2200) ("office" "office" "Escritorio" 2900))
        (setq idx 1)
        (repeat (fix (cg:get (car spec) params))
          (setq program (append program (list (cl:spec (cadr spec) (strcat (nth 2 spec) " " (itoa idx))
            (+ (nth 3 spec) (* 100 (fix (* 5 (cg:rand))))))))) (setq idx (1+ idx))))
      (setq program (cg:shuffle program))
      ;; Similar-depth front rooms avoid enlarging a single bathroom to match a bedroom.
      (if (= layout 3) (setq program (cl:depth-sort program)))
      (if (and (= layout 3) (< (length program) 4)) (setq err "Organizacao central exige ao menos quatro ambientes privados/servico; selecione frente ou fundo."))
      (setq x0 (+ ox (cg:get "side" params)) x1 (+ x0 (cg:get "house_width" params))
        front (max (cg:get "front" params) (if (> parking 0) 6500 0)) y0 (+ oy front)
        *cl-xa* (+ x0 (/ *cl-te* 2.0)) *cl-xb* (- x1 (/ *cl-te* 2.0)) *cl-ya* (+ y0 (/ *cl-te* 2.0))
        socialdepth (+ 3600 (* 100 (fix (* 6 (cg:rand)))) *cl-ti*))
      (if (= layout 3)
        (progn (setq nfirst (fix (/ (length program) 2)) idx 0)
          (foreach item program (if (< idx nfirst) (setq groupa (append groupa (list item))) (setq groupb (append groupb (list item)))) (setq idx (1+ idx)))
          (setq da (cl:section-depth groupa nil) db (cl:section-depth groupb nil)))
        (if (= layout 2) (setq da (cl:section-depth program nil) db 0) (setq da 0 db (cl:section-depth program nil))))
      (setq total (+ da socialdepth db) *cl-yb* (+ *cl-ya* total) ye (+ *cl-yb* (/ *cl-te* 2.0))
        socialya (+ *cl-ya* da) socialyb (+ socialya socialdepth))
      (if (> ye (- (+ oy (cg:get "lot_depth" params)) (cg:get "rear" params)))
        (setq err (strcat "Esta organizacao precisa de " (rtos (/ (+ total *cl-te*) 1000.0) 2 2) "m de profundidade construida. Aumente lote/reduza programa ou selecione outra organizacao.")))
      (if (< (- (cg:get "house_width" params) (* 2 *cl-te*) (if (= integration 3) (* (if (= (cg:get "dining" params) 1) 2 1) *cl-ti*) (if (= integration 2) *cl-ti* 0)))
          (if (= (cg:get "dining" params) 1) 8300 5600)) (setq err "Largura insuficiente para sala/cozinha/jantar e mobiliario neste perfil. Aumente largura ou altere integracao."))
      (if (and (> parking 0) (< (cg:get "lot_width" params) (+ (* parking 2600) 1200))) (setq err "Garagem e percurso pedestre nao cabem na largura do lote."))
      (if err (list (cons "error" err))
        (progn
          (if (= layout 3) (cl:section groupa *cl-ya* socialya nil))
          (if (= layout 2) (cl:section program *cl-ya* socialya nil))
          (cl:social socialya socialyb integration (fix (cg:get "dining" params)))
          (if (/= layout 2) (cl:section (if (= layout 3) groupb program) socialyb *cl-yb* nil))
          (setq *cl-footprint* (list (list x0 y0) (list x1 y0) (list x1 ye) (list x0 ye)))
          (cl:articulate (= layout 2))
          (cl:build-walls) (cl:remeasure)
          (foreach room *cl-rooms*
            (if (not (member (cg:get "kind" room) '("social" "corridor")))
              (cl:zone (cg:get "kind" room) (cg:get "name" room) (cg:get "bounds" room) (cg:get "id" room))))
          (cl:openings) (cl:zone-windows)
          (if (> parking 0)
            (progn
              (setq garagewidth (* parking 2600) gx (max ox (min (- (+ ox (cg:get "lot_width" params)) garagewidth 1200) (- (car *cl-entry-center*) garagewidth 600)))
                gy (- y0 6500) pathstart (list (+ gx garagewidth 600) (+ gy 4300))
                pathcorner (list (car *cl-entry-center*) (- y0 600))
                entrypath (list (cons "points" (list pathstart (list (car pathstart) (cadr pathcorner)) pathcorner *cl-entry-center*))
                  (cons "width" 1200) (cons "length" (+ (- (cadr pathcorner) (cadr pathstart)) (abs (- (car pathcorner) (car pathstart))) (- (cadr *cl-entry-center*) (cadr pathcorner))))))
            (setq outdoor (list (list (cons "id" "EXT-GARAGE") (cons "kind" "garage") (cons "name" "Garagem descoberta")
              (cons "spaces" parking) (cons "bounds" (list gx gy (+ gx garagewidth) (+ gy 5000))))))))
          (setq rearspace (- (+ oy (cg:get "lot_depth" params)) ye))
          (if (and (= (cg:opt "terrace" params 1) 1) (>= rearspace 1800))
            (setq outdoor (append outdoor (list (list (cons "id" "EXT-TERRACE") (cons "kind" "terrace") (cons "name" "Convivencia descoberta")
              (cons "bounds" (list x0 ye (min x1 (+ x0 4000)) (+ ye (min 2500 rearspace)))))))))
          ;; Rear access through the corridor when possible, preserving private rooms.
          (foreach item *cg-walls*
            (if (and (= (length (cg:get "room_ids" item)) 1)
                (= (cg:get "kind" (cl:room-by-id (car (cg:get "room_ids" item)))) "corridor")
                (equal (cadr (cg:get "start" item)) *cl-yb* 0.01) (equal (cadr (cg:get "end" item)) *cl-yb* 0.01))
              (cl:door item (car (cg:get "room_ids" item)) nil 900 "hinged")))
          (setq checks (list
            (list (cons "rule_id" "PROGRAM") (cons "status" "pass") (cons "message" "Quantidades funcionais preservadas em zones; integracao altera numero de recintos."))
            (list (cons "rule_id" "ACCESS_GRAPH") (cons "status" (if (cl:reachable) "pass" "fail")) (cons "message" "Grafo de portas conecta todos os recintos ao exterior; nao equivale a rota acessivel."))
            (list (cons "rule_id" "MAIN_ARRIVAL") (cons "status" (if (and *cl-main-entry* (or (= parking 0) (<= (cg:get "length" entrypath) 6000))) "pass" "fail")) (cons "message" "Entrada frontal conectada a garagem por faixa pedestre 1.20m; distancia alvo ate 6m e criterio de projeto, nao norma."))
            (list (cons "rule_id" "BH") (cons "status" "not_evaluated") (cons "message" "Faixas hipoteticas; garagem e area externa dependem das regras reais do lote."))
            (list (cons "rule_id" "DAYLIGHT_THERMAL") (cons "status" "not_evaluated") (cons "message" "Aberturas externas previstas; norte informativo. Insolacao, ventilacao, materiais e entorno nao simulados."))))
          (setq circarea 0.0 netarea 0.0 winarea 0.0 wincount 0)
          (foreach room *cl-rooms* (setq netarea (+ netarea (cg:get "net_area_m2" room)))
            (if (= (cg:get "kind" room) "corridor") (setq circarea (+ circarea (cg:get "net_area_m2" room)))))
          (foreach item *cg-openings* (if (= (cg:get "kind" item) "window")
            (setq wincount (1+ wincount) winarea (+ winarea (/ (* (cg:get "width" item) (cg:get "height" item)) 1000000.0)))))
          (setq model (list (cons "schema_version" "1.0") (cons "project_id" (cg:opt "project_id" params "CG-DEMO")) (cons "units" "mm")
            (cons "origin" (list ox oy 0.0)) (cons "algorithm_version" "architectural-0.4") (cons "seed" (cg:get "seed" params))
            (cons "front_effective" front) (cons "layout" layout) (cons "integration" integration) (cons "north" north) (cons "north_degrees" north) (cons "occupants" occupants)
            (cons "layout_name" (nth (1- layout) '("Social na frente" "Convivencia no fundo" "Convivencia central")))
            (cons "integration_name" (nth (1- integration) '("Integrada" "Semi-integrada" "Separada")))
            (cons "circulation_area_m2" circarea) (cons "circulation_fraction" (/ circarea netarea))
            (cons "windows_count" wincount) (cons "window_area_m2" winarea)
            (cons "site_mode" "hypothetical_flat") (cons "site_bounds" (list ox oy (+ ox (cg:get "lot_width" params)) (+ oy (cg:get "lot_depth" params))))
            (cons "house_bounds" (list x0 y0 x1 ye)) (cons "footprint" *cl-footprint*) (cons "main_entry_id" *cl-main-entry*) (cons "entry_path" entrypath)
            (cons "gross_area_m2" (cl:polygon-area *cl-footprint*))
            (cons "wall_internal" *cl-ti*) (cons "wall_external" *cl-te*) (cons "walls" *cg-walls*) (cons "openings" *cg-openings*)
            (cons "rooms" *cl-rooms*) (cons "zones" *cl-zones*) (cons "outdoor" outdoor) (cons "furniture" nil)
            (cons "slab" (list (cons "bounds" (list x0 y0 x1 ye)) (cons "outline" *cl-footprint*) (cons "thickness" 150))) (cons "validations" checks)))
          (if (not (cl:reachable)) (list (cons "error" "Candidato rejeitado: recinto sem caminho de portas ate exterior."))
            (cg:furnish-model (cg:with-roof model) params)))))))
(princ)




;;; Bounded deterministic backtracking: preserve the program and furniture checks.
(defun cg:generate (params / model factors factor attempts result)
 (setq factors '(1.0 0.75 0.5) model nil attempts 0)
 (while factors
  (setq factor (car factors) factors (cdr factors) attempts (1+ attempts)
   model (cl:generate-candidate (cons (cons "_recess_scale" factor) params)))
  (if (not (cg:get "error" model))
   (progn (setq model (append model (list (cons "recess_scale" factor) (cons "geometry_attempts" attempts)))) (setq factors nil))
   (if (not (wcmatch (cg:get "error" model) "Conjunto*")) (setq factors nil))))
 model)
(princ)
