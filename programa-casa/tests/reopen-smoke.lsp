(defun reopen:run (report dxfpath / out ss snap)
 (setq out (open report "w") ss (ssget "_X"))
 (write-line (strcat "ENTITIES=" (itoa (if ss (sslength ss) 0))) out)
 (setq ss (ssget "_X" '((0 . "DIMENSION"))))
 (write-line (strcat "DIMENSIONS=" (itoa (if ss (sslength ss) 0))) out)
 (setq snap (cg:stored-json "CG-EXEMPLO-001"))
 (write-line (strcat "SNAPSHOT=" (if snap "PASS" "FAIL")) out)
 (write-line (strcat "SNAPSHOT_LENGTH=" (itoa (if snap (strlen snap) 0))) out)
 (close out)
 (setvar "FILEDIA" 0)
 (command-s "_.DXFOUT" dxfpath "16")
 (princ))
