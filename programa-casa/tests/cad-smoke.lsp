(defun smoke:lines (file / f line result)
 (setq f (open file "r") result nil)
 (if f (progn (while (setq line (read-line f)) (setq result (cons line result))) (close f))) result)
(defun smoke:run (jsonfile reportfile dwgfile / model params result out dlg before vars key dclfile)
 (setq params (ct:params 42))
 (setq params (subst (cons "lot_width" 12000.0) (assoc "lot_width" params) params))
 (setq params (subst (cons "bathrooms" 1) (assoc "bathrooms" params) params))
 (setq params (append params '(("project_id" . "CG-EXEMPLO-001"))))
 (foreach key '("bedrooms" "bathrooms" "living" "kitchens" "laundry" "dining" "office" "seed")
  (setq params (subst (cons key (float (cg:get key params))) (assoc key params) params)))
 (setq params (append '(("wall_internal" . 150.0) ("wall_external" . 200.0)) params))
 (setq model (cg:generate params))
 (setq out (open reportfile "w"))
 (setvar "INSUNITS" 4)
 (setq dclfile (cg:embedded-dialog))
 (write-line (strcat "EMBEDDED_DCL=" (if (equal (smoke:lines dclfile) (smoke:lines (strcat *casa-dir* "/casa.dcl"))) "PASS" "FAIL")) out)
 (setq dlg (load_dialog dclfile))
 (write-line (strcat "DCL_LOAD=" (itoa dlg)) out)
 (if (> dlg 0) (unload_dialog dlg))
 (vl-file-delete dclfile)
 (setq vars nil)
 (foreach key '("OSMODE" "CLAYER" "DIMTXT" "DIMLFAC" "DIMPOST")
  (setq vars (cons (cons key (getvar key)) vars)))
 (setq result (cg:commit model))
 (write-line (strcat "COMMIT=" (if result "PASS" "FAIL")) out)
 (write-line (strcat "SNAPSHOT=" (if (= (cg:stored-json "CG-EXEMPLO-001") (cg:json model)) "PASS" "FAIL")) out)
 (foreach key vars
  (write-line (strcat "RESTORE_" (car key) "=" (if (equal (cdr key) (getvar (car key))) "PASS" "FAIL")) out))
 (write-line (strcat "DIMENSIONS=" (itoa (sslength (ssget "_X" '((0 . "DIMENSION")))))) out)
 (write-line (strcat "ENTITIES=" (itoa (sslength (ssget "_X")))) out)
 (write-line (strcat "EXPORT=" (if (cg:write-json model jsonfile) "PASS" "FAIL")) out)
 (close out)
 (setvar "FILEDIA" 0)
 (command-s "_.ZOOM" "_Extents")
 (command-s "_.QSAVE")
 (princ "\nSMOKE_COMPLETE") (princ))
