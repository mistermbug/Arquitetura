(defun ft:run (path / fh kind zone items model a b failures)
 (setq fh (open path "w") failures 0 model nil)
 (foreach spec '(("bedroom" 3400 3200) ("living" 3000 3500) ("dining" 2700 3500) ("kitchen" 2600 3500) ("bathroom" 3400 2200) ("laundry" 3400 1900) ("office" 3400 2800) ("garage" 2800 5000) ("veranda" 3500 2000))
  (setq zone (list (cons "kind" (car spec)) (cons "id" "Z1") (cons "room_id" "R1") (cons "bounds" (list 0 0 (cadr spec) (caddr spec)))) items (cf:place zone model T))
  (write-line (strcat (if items "PASS " "FAIL ") (car spec) " items=" (itoa (length items))) fh)
  (if (not items) (setq failures (1+ failures))))
  (foreach loc '((0 600) (3400 600) (600 0) (2800 0) (0 2700) (3400 2700))
  (setq zone (list (cons "kind" "bedroom") (cons "id" "Z1") (cons "room_id" "R1") (cons "bounds" '(0 0 3400 3200)))
   model (list (cons "openings" (list (list (cons "kind" "door") (cons "center" loc) (cons "width" 800)))))
   items (cf:place zone model T))
  (write-line (strcat (if items "PASS " "FAIL ") "BEDROOM_DOOR " (vl-princ-to-string loc)) fh)
  (if (not items) (setq failures (1+ failures))))
 (setq a (cf:item "sofa" '(0 0 1000 1000) 800 nil) b (cf:item "desk" '(500 500 1500 1500) 800 nil))
 (if (cf:valid (list a b) '(0 0 3000 3000) nil) (progn (write-line "FAIL REJECT_COLLISION" fh) (setq failures (1+ failures))) (write-line "PASS REJECT_COLLISION" fh))
 (if (cf:valid (list a) '(0 0 3000 3000) '((0 0 900 900))) (progn (write-line "FAIL REJECT_DOOR" fh) (setq failures (1+ failures))) (write-line "PASS REJECT_DOOR" fh))
 (if (cf:valid (list a) '(0 0 500 500) nil) (progn (write-line "FAIL REJECT_OUTSIDE" fh) (setq failures (1+ failures))) (write-line "PASS REJECT_OUTSIDE" fh))
 (setq model (list
   (cons "walls" (list (list (cons "id" "W1") (cons "start" '(0 0)) (cons "end" '(0 4000)) (cons "thickness" 200))))
   (cons "openings" (list (list (cons "kind" "window") (cons "wall_id" "W1") (cons "center" '(0 2000)) (cons "width" 1200) (cons "sill" 900))))))
 (setq a (cf:item "wardrobe" '(100 1600 700 2500) 2200 nil) b (cf:item "desk" '(100 1600 700 2500) 750 nil))
 (if (cf:window-clear (list a) model) (progn (write-line "FAIL WINDOW_TALL" fh) (setq failures (1+ failures))) (write-line "PASS WINDOW_TALL" fh))
 (if (not (cf:window-clear (list b) model)) (progn (write-line "FAIL WINDOW_LOW" fh) (setq failures (1+ failures))) (write-line "PASS WINDOW_LOW" fh))
 (setq *cf-garage-spaces* 2 zone (list (cons "kind" "garage") (cons "id" "G1") (cons "bounds" '(0 0 5200 5000))) items (cf:place zone nil nil) *cf-garage-spaces* nil)
 (if (/= (length items) 2) (progn (write-line "FAIL TWO_CARS" fh) (setq failures (1+ failures))) (write-line "PASS TWO_CARS" fh)) (write-line (strcat "COMPLETE failures=" (itoa failures)) fh) (close fh) (princ))
