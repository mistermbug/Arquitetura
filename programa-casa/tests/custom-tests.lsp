(defun te:check (ok label)
 (write-line (strcat (if ok "PASS " "FAIL ") label) te:out)
 (if (not ok) (setq te:failed (1+ te:failed))))
(defun te:read (file / f s ln) (setq f (open file "r") s "") (while (setq ln (read-line f)) (setq s (strcat s ln))) (close f) s)
(defun te:run (source target)
 (setq te:out (open (strcat target "/report.txt") "w") te:failed 0)
 (setq m (cj:parse (te:read source)) pid (cg:get "project_id" m))
 (te:check (equal m (cj:parse (cg:json m)) 0.00001) "JSON roundtrip")
 (te:check (= (cg:json (cj:parse "{\"a\":true,\"b\":false,\"c\":null}")) "{\"a\":true,\"b\":false,\"c\":null}") "JSON literals")
 (te:check (vl-catch-all-error-p (vl-catch-all-apply 'cj:parse '("{invalid}"))) "Malformed JSON rejected")
 (setvar "INSUNITS" 4) (setvar "TILEMODE" 1)
 (cg:commit m)
 (te:check (= (cg:stored-json pid) (cg:json m)) "Snapshot original")
 (princ))
(defun te:edit (target)
 (setq f (car (cg:get "furniture" m)) b (cg:get "bounds" f))
 (setq resized (ce:resize f (* 0.9 (- (nth 2 b) (car b))) (* 0.9 (- (nth 3 b) (cadr b))) 800))
 (te:check (not (ce:validate resized m)) "Valid shrink")
 (setq before (cg:stored-json pid) n (sslength (ssget "_X" '((8 . "CASA_PAREDES")))))
 (write-line (strcat "UNDOCTL before=" (itoa (getvar "UNDOCTL"))) te:out)
 (setq result (ce:apply m resized))
 (write-line (strcat "UNDOCTL after=" (itoa (getvar "UNDOCTL"))) te:out)
 (te:check result "Apply edit")
 (setq after (cg:stored-json pid))
 (setq debug (open (strcat target "/snapshot-debug.json") "w")) (write-line after debug) (close debug)
 (te:check (/= before after) "Persisted JSON changed")
 (te:check (= (cg:get "height" (car (cg:get "furniture" (cj:parse after)))) 800) "New height persisted")
 (te:check (= n (sslength (ssget "_X" '((8 . "CASA_PAREDES"))))) "Walls untouched")
 (te:check (ce:validate (ce:resize f 15000 15000 2800) m) "Oversized collision rejected")
 (princ))
(defun te:finish (target)
 (te:check (= before (cg:stored-json pid)) "Undo restores JSON and drawing")
 (write-line (strcat "UNDOCTL before=" (itoa (getvar "UNDOCTL"))) te:out)
 (setq result (ce:apply m resized))
 (write-line (strcat "UNDOCTL after=" (itoa (getvar "UNDOCTL"))) te:out)
 (cg:write-json result (strcat target "/resized.json"))
 (command-s "_.QSAVE")
 (write-line (strcat "COMPLETE failed=" (itoa te:failed)) te:out) (close te:out) (princ))

(defun te:reopen (target / ss m pid item b adjusted angle r w d rb)
 (setq te:out (open (strcat target "/report.txt") "w") te:failed 0
  ss (ssget "_X" '((-3 ("CASA_BH")))))
 (setq pid (car (ce:identity (ssname ss 0))) m (cj:parse (cg:stored-json pid)) item (car (cg:get "furniture" m)) b (cg:get "bounds" item))
 (te:check (= (cg:get "height" item) 800) "Reopened height from persisted snapshot")
 (te:check (= (cg:get "dimension_revision" item) 1) "Reopened revision")
 (te:check (ce:entities pid (cg:get "id" item)) "Reopened drawing identity")
 (foreach angle '(0 90 180 270)
  (setq r (ce:put "rotation" angle item) w (* 0.95 (- (nth 2 b) (car b))) d (* 0.95 (- (nth 3 b) (cadr b))))
  (if (member angle '(90 270)) (setq r (ce:resize r d w 850)) (setq r (ce:resize r w d 850)))
  (setq rb (cg:get "bounds" r))
  (te:check (and (equal (- (nth 2 rb) (car rb)) w 0.01) (equal (- (nth 3 rb) (cadr rb)) d 0.01)) (strcat "Local dimensions rotation " (itoa angle))))
 (setq adjusted (ce:resize item (* 0.95 (- (nth 2 b) (car b))) (* 0.95 (- (nth 3 b) (cadr b))) 850))
 (te:check (not (ce:validate adjusted m)) "Reopened edit clearance")
 (te:check (ce:apply m adjusted) "Edit after reopening")
 (te:check (= (cg:get "dimension_revision" (car (cg:get "furniture" (cj:parse (cg:stored-json pid))))) 2) "Second revision persisted")
 (write-line (strcat "COMPLETE failed=" (itoa te:failed)) te:out) (close te:out) (princ))
