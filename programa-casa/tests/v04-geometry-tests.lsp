;;; Contour and arrival regression checks; call (t4:geometry model).
(defun t4:geometry (model / errors footprint bounds path points entry garage lengthcalc a b walls wall rooms room ids)
  (setq footprint (cg:get "footprint" model) bounds (cg:get "house_bounds" model))
  (if (< (length footprint) 6) (setq errors (cons "Expected articulated footprint" errors)))
  (if (>= (cl:polygon-area footprint) (- (cl:area bounds) 0.01)) (setq errors (cons "Footprint must differ from bounding rectangle" errors)))
  (if (not (equal footprint (cg:get "outline" (cg:get "slab" model)) 0.01)) (setq errors (cons "Slab contour mismatch" errors)))
  (if (> (abs (- (cl:polygon-area footprint) (cg:get "gross_area_m2" model))) 0.001) (setq errors (cons "Gross area mismatch" errors)))
  (foreach wall (cg:get "walls" model)
    (if (not (equal (cg:get "thickness" wall) (cg:get (if (= (length (cg:get "room_ids" wall)) 1) "wall_external" "wall_internal") model) 0.01))
      (setq errors (cons "Wall thickness versus ownership mismatch" errors))))
  (foreach a (cg:get "openings" model) (if (= (cg:get "id" a) (cg:get "main_entry_id" model)) (setq entry a)))
  (if (not entry) (setq errors (cons "Main entry missing" errors)))
  (if (and entry (> (abs (- (cadr (cg:get "center" entry)) (+ (cadr bounds) (/ (cg:get "wall_external" model) 2.0)))) 0.01))
    (setq errors (cons "Main entry must face front arrival" errors)))
  (foreach a (cg:get "outdoor" model) (if (= (cg:get "kind" a) "garage") (setq garage a)))
  (if garage
    (progn
      (setq path (cg:get "entry_path" model) points (cg:get "points" path) lengthcalc 0.0)
      (if (or (not path) (> (cg:get "length" path) 6000)) (setq errors (cons "Garage arrival absent or over six metres" errors)))
      (if (not (equal (last points) (cg:get "center" entry) 0.01)) (setq errors (cons "Arrival does not reach main entry" errors)))
      (while (cdr points)
        (setq a (car points) b (cadr points) lengthcalc (+ lengthcalc (distance a b)) points (cdr points)))
      (if (> (abs (- lengthcalc (cg:get "length" path))) 0.01) (setq errors (cons "Arrival length mismatch" errors)))))
  (reverse errors))
(princ)

(defun t4:run (file / out layout integration seed model problems count)
 (setq out (open file "w") count 0)
 (foreach layout '(1 2 3) (foreach integration '(1 2 3) (foreach seed '(1 42 91 101 333)
  (setq model (cg:generate (t3:params layout integration seed)))
  (if (cg:get "error" model) (write-line (strcat "FAIL " (itoa layout) ":" (itoa integration) ":" (itoa seed) " " (cg:get "error" model)) out)
   (progn
    (setq problems (t4:geometry model))
    (if problems (write-line (strcat "FAIL " (vl-prin1-to-string problems)) out) (setq count (1+ count))))))))
 (write-line (strcat "COMPLETE passed=" (itoa count) "/45") out) (close out))
(defun t4:path-clear (model / points a b box vehicle errors bounds margin)
 (setq points (cg:get "points" (cg:get "entry_path" model)) bounds (cg:get "house_bounds" model) margin 600)
 (while (cdr points)
  (setq a (car points) b (cadr points))
  ;; Flat end at external facade; final crossing of threshold is intentional.
  (setq box (if (equal (car a) (car b) 0.01)
    (list (- (car a) margin) (min (cadr a) (cadr b)) (+ (car a) margin) (min (cadr bounds) (max (cadr a) (cadr b))))
    (list (min (car a) (car b)) (- (cadr a) margin) (max (car a) (car b)) (+ (cadr a) margin))))
  (if (t3:overlap box bounds) (setq errors (cons "Pedestrian band intersects house" errors)))
  (foreach vehicle (cg:get "outdoor" model) (if (and (= (cg:get "kind" vehicle) "garage") (t3:overlap box (cg:get "bounds" vehicle))) (setq errors (cons "Pedestrian band intersects parking bay" errors))))
  (foreach vehicle (cg:get "furniture" model) (if (and (= (cg:get "kind" vehicle) "car") (t3:overlap box (cg:get "bounds" vehicle))) (setq errors (cons "Pedestrian band intersects car" errors))))
  (setq points (cdr points)))
 errors)
(defun t4:run-extra (file / out layout parking seed model params problems pass)
 (setq out (open file "w") pass 0)
 (foreach parking '(0 2) (foreach layout '(1 2 3) (foreach seed '(1 42 91 101 333)
  (setq params (t3:params layout 1 seed) params (subst (cons "parking" parking) (assoc "parking" params) params)
    model (cg:generate params))
  (if (cg:get "error" model) (write-line (strcat "FAIL P" (itoa parking) " L" (itoa layout) " " (cg:get "error" model)) out)
   (progn (setq problems (append (t4:geometry model) (t4:path-clear model)))
    (if problems (write-line (strcat "FAIL " (vl-prin1-to-string problems)) out) (setq pass (1+ pass))))))))
 (foreach layout '(1 2 3)
  (setq params (t3:params layout 1 42) params (subst '("bedrooms" . 1.0) (assoc "bedrooms" params) params)
    params (subst '("bathrooms" . 2.0) (assoc "bathrooms" params) params) params (subst '("occupants" . 2.0) (assoc "occupants" params) params)
    model (cg:generate params))
  (if (cg:get "error" model) (write-line (strcat "FAIL small-program " (cg:get "error" model)) out)
   (progn (setq problems (append (t4:geometry model) (t4:path-clear model)))
    (if problems (write-line (strcat "FAIL " (vl-prin1-to-string problems)) out) (setq pass (1+ pass))))))
 (write-line (strcat "COMPLETE extras=" (itoa pass) "/21") out) (close out))
