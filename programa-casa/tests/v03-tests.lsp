(defun t3:check (value message)
 (if value (setq t3:pass (1+ t3:pass))
  (progn (setq t3:fail (1+ t3:fail)) (write-line (strcat "FAIL " message) t3:out))))
(defun t3:params (layout integration seed)
 (list '("lot_width" . 12000.0) '("lot_depth" . 30000.0) '("house_width" . 9000.0)
 '("front" . 5500.0) '("rear" . 3000.0) '("side" . 1500.0) '("wall_internal" . 150.0)
 '("wall_external" . 200.0) '("corridor" . 1200.0) '("height" . 2800.0)
 '("bedrooms" . 3.0) '("bathrooms" . 1.0) '("living" . 1.0) '("kitchens" . 1.0)
 '("laundry" . 1.0) '("dining" . 1.0) '("office" . 0.0) '("occupants" . 4.0)
 '("parking" . 1.0) '("terrace" . 1.0) '("north" . 30.0) '("furniture" . 1.0)
 (cons "layout" (float layout)) (cons "integration" (float integration)) (cons "seed" (float seed))))
(defun t3:inside (a b)
 (and (>= (car a) (- (car b) 0.1)) (>= (cadr a) (- (cadr b) 0.1))
  (<= (nth 2 a) (+ (nth 2 b) 0.1)) (<= (nth 3 a) (+ (nth 3 b) 0.1))))
(defun t3:overlap (a b)
 (and (< (car a) (- (nth 2 b) 0.1)) (> (nth 2 a) (+ (car b) 0.1))
  (< (cadr a) (- (nth 3 b) 0.1)) (> (nth 3 a) (+ (cadr b) 0.1))))
(defun t3:audit (m / r s b rooms f host o w a z c kinds kind count)
 (setq rooms (cg:get "rooms" m))
 (foreach r rooms
  (setq b (cg:get "bounds" r))
  (t3:check (t3:inside b (cg:get "house_bounds" m)) "room outside house")
  (t3:check (and (> (- (nth 2 b) (car b)) 0) (> (- (nth 3 b) (cadr b)) 0)) "empty room")
  (foreach s rooms (if (/= (cg:get "id" r) (cg:get "id" s))
   (t3:check (not (t3:overlap b (cg:get "bounds" s))) "overlapping rooms"))))
 (foreach f (cg:get "furniture" m)
  (setq host (cg:find-id (cg:get "room_id" f) (append rooms (cg:get "outdoor" m))))
  (t3:check (and host (t3:inside (cg:get "bounds" f) (cg:get "bounds" host))) "furniture host bounds")
  (foreach s (cg:get "furniture" m) (if (/= (cg:get "id" f) (cg:get "id" s))
   (t3:check (not (t3:overlap (cg:get "bounds" f) (cg:get "bounds" s))) "furniture collision"))))
 (foreach o (cg:get "openings" m)
  (setq w (cg:find-id (cg:get "wall_id" o) (cg:get "walls" m)))
  (t3:check w "opening wall missing")
  (if w (progn (setq a (cg:get "start" w) z (cg:get "end" w) c (cg:get "center" o))
   (t3:check (< (abs (- (+ (distance a c) (distance c z)) (distance a z))) 0.1) "opening off wall axis")
   (t3:check (and (>= (distance a c) (/ (cg:get "width" o) 2))
    (>= (distance c z) (/ (cg:get "width" o) 2))) "opening exceeds wall"))))
 (foreach r (cg:get "outdoor" m)
  (t3:check (t3:inside (cg:get "bounds" r) (cg:get "site_bounds" m)) "outdoor outside site")
  (t3:check (not (t3:overlap (cg:get "bounds" r) (cg:get "house_bounds" m))) "outdoor overlaps house"))
 (setq kinds '(("bedroom" . 3) ("bathroom" . 1) ("living" . 1) ("kitchen" . 1) ("laundry" . 1) ("dining" . 1)))
 (foreach kind kinds (setq count 0)
  (foreach r (cg:get "zones" m) (if (= (cg:get "kind" r) (car kind)) (setq count (1+ count))))
  (t3:check (= count (cdr kind)) (strcat "program count " (car kind)))))
(defun t3:run (folder / t3:out t3:pass t3:fail layout integration seed p m again tag f drawset originx before dcl)
 (setq t3:out (open (strcat folder "/report.txt") "w") t3:pass 0 t3:fail 0 drawset nil)
 (setvar "INSUNITS" 4)
 (foreach layout '(1 2 3)
  (foreach integration '(1 2 3)
   (foreach seed '(1 42 91)
    (setq p (t3:params layout integration seed) tag (strcat (itoa layout) "-" (itoa integration) "-" (itoa seed))
     p (cons (cons "project_id" (strcat "V03-" tag)) p) m (cg:generate p))
    (t3:check (not (cg:get "error" m)) (strcat tag " " (cg:opt "error" m "")))
    (if (not (cg:get "error" m))
     (progn (t3:audit m)
      (setq again (cg:generate p)) (t3:check (equal m again) (strcat "repeatability " tag))
      (cg:write-json m (strcat folder "/" tag ".json"))
      (if (and (= seed 42) (= integration layout)) (setq drawset (append drawset (list p)))))))))
 ;; Fractional room counts must be rejected, never truncated into another program.
 (setq p (cons '("bedrooms" . 2.5) (t3:params 1 1 42)))
 (t3:check (cg:get "error" (cg:generate p)) "fractional count accepted")
 (setq p (cons '("house_width" . 20000.0) (t3:params 1 1 42)))
 (t3:check (cg:get "error" (cg:generate p)) "oversized house accepted")
 (setq originx 0)
 (foreach p drawset
  (setq m (cg:generate (cons (cons "origin_x" originx) p)))
  (t3:check (cg:commit m) "native CAD commit")
  (t3:check (= (cg:stored-json (cg:get "project_id" m)) (cg:json m)) "CAD persisted snapshot")
  (cg:write-json m (strcat folder "/desenho-" (itoa (1+ (fix (/ originx 41000)))) ".json"))
  (setq originx (+ originx 41000)))
 (setq dcl (cg:embedded-dialog))
 (t3:check (findfile dcl) "embedded DCL extraction") (vl-file-delete dcl)
 (write-line (strcat "COMPLETE passed=" (itoa t3:pass) " failed=" (itoa t3:fail) " drawings=" (itoa (length drawset))) t3:out)
 (close t3:out)
 (command-s "_.ZOOM" "_Extents")
 (setvar "FILEDIA" 0) (command-s "_.QSAVE")
 (command-s "_.DXFOUT" (strcat folder "/comparacao.dxf") "_Version" "2018" "16")
 (princ))

(defun t3:reopen (folder source / t3:out t3:pass t3:fail n pid snapshot file text entity data tagged)
 (setq t3:out (open (strcat folder "/report.txt") "w") t3:pass 0 t3:fail 0 n 1)
 (foreach pid '("V03-1-1-42" "V03-2-2-42" "V03-3-3-42")
  (setq snapshot (cg:stored-json pid) file (open (strcat source "/desenho-" (itoa n) ".json") "r"))
  (setq text (read-line file)) (close file)
  (t3:check (= snapshot text) (strcat "reopened snapshot differs " pid))
  (setq n (1+ n)))
 (t3:check (> (sslength (ssget "_X" '((0 . "DIMENSION")))) 20) "native dimensions lost")
 (write-line (strcat "COMPLETE passed=" (itoa t3:pass) " failed=" (itoa t3:fail) " drawings=3") t3:out)
 (close t3:out) (princ))
