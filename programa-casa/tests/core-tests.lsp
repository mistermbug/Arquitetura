;;; Regression tests executed by genuine AutoLISP in an isolated drawing.
(defun ct:assert (condition description /)
  (if condition
    (progn (setq ct:passed (1+ ct:passed)) (write-line (strcat "PASS " description) ct:file))
    (progn (setq ct:failed (1+ ct:failed)) (write-line (strcat "FAIL " description) ct:file))))

(defun ct:params (seed /)
  (list (cons "lot_width" 14000.0) (cons "lot_depth" 30000.0)
    (cons "front" 5000.0) (cons "rear" 3000.0) (cons "side" 1500.0)
    (cons "wall" 150.0) (cons "corridor" 1200.0) (cons "house_width" 9000.0)
    (cons "height" 2800.0) (cons "dining" 0) (cons "office" 0)
    (cons "bedrooms" 3) (cons "bathrooms" 2) (cons "living" 1)
    (cons "kitchens" 1) (cons "laundry" 1)
    (cons "seed" seed) (cons "furniture" 1)))

(defun ct:get (key object) (cdr (assoc key object)))

(defun ct:bounds-p (b /)
  (and (= (length b) 4) (< (nth 0 b) (nth 2 b)) (< (nth 1 b) (nth 3 b))))

(defun ct:inside-p (inner outer /)
  (and (>= (nth 0 inner) (- (nth 0 outer) 0.001))
       (>= (nth 1 inner) (- (nth 1 outer) 0.001))
       (<= (nth 2 inner) (+ (nth 2 outer) 0.001))
       (<= (nth 3 inner) (+ (nth 3 outer) 0.001))))

(defun ct:geometry (model label / rooms walls slab r b w a z o host length-wall offset width parent candidate other)
  (setq rooms (ct:get "rooms" model) walls (ct:get "walls" model)
        slab (ct:get "bounds" (ct:get "slab" model)))
  (ct:assert (ct:bounds-p slab) (strcat label " slab positive"))
  (foreach r rooms
    (setq b (ct:get "bounds" r))
    (ct:assert (ct:bounds-p b) (strcat label " positive room " (ct:get "id" r)))
    (ct:assert (ct:inside-p b slab) (strcat label " room inside slab " (ct:get "id" r))))
  (foreach w walls
    (ct:assert (> (distance (ct:get "start" w) (ct:get "end" w)) 10.0)
      (strcat label " nonzero wall " (ct:get "id" w))))
  (foreach o (ct:get "openings" model)
    (setq host nil)
    (foreach w walls (if (= (ct:get "id" w) (ct:get "wall_id" o)) (setq host w)))
    (ct:assert host (strcat label " opening has host " (ct:get "id" o)))
    (if host
      (progn
        (setq a (ct:get "start" host) z (ct:get "end" host)
              length-wall (distance a z) offset (distance a (ct:get "center" o)) width (ct:get "width" o))
        (ct:assert (equal (+ offset (distance (ct:get "center" o) z)) length-wall 0.01)
          (strcat label " opening on axis " (ct:get "id" o)))
        (ct:assert (and (> (- offset (/ width 2.0)) 0.0) (< (+ offset (/ width 2.0)) length-wall))
          (strcat label " opening fits host " (ct:get "id" o))))))
  (foreach r (ct:get "furniture" model)
    (setq b (ct:get "bounds" r))
    (ct:assert (ct:bounds-p b) (strcat label " positive furniture " (ct:get "id" r)))
    (ct:assert (ct:inside-p b slab) (strcat label " furniture inside slab " (ct:get "id" r)))
    (setq parent nil)
    (foreach candidate rooms
      (if (= (ct:get "id" candidate) (ct:get "room_id" r)) (setq parent candidate)))
    (ct:assert (and parent (ct:inside-p b (ct:get "bounds" parent)))
      (strcat label " furniture inside assigned room " (ct:get "id" r)))))

(defun ct:program (model params / mapping actual room)
  (foreach mapping '(("bedrooms" "bedroom") ("bathrooms" "bathroom") ("living" "living")
    ("kitchens" "kitchen") ("laundry" "laundry") ("dining" "dining") ("office" "office"))
    (setq actual 0)
    (foreach room (ct:get "rooms" model)
      (if (= (ct:get "kind" room) (cadr mapping)) (setq actual (1+ actual))))
    (ct:assert (= actual (ct:get (car mapping) params)) (strcat "requested count " (car mapping)))))

(defun ct:wall-profile (model ti te / room b house last-bottom last-top rows sum-depth wall)
  (setq house (ct:get "house_bounds" model) last-bottom nil last-top nil rows 0 sum-depth 0.0)
  (foreach wall (ct:get "walls" model)
    (ct:assert (equal (ct:get "thickness" wall) (if (= (ct:get "wall_role" wall) "external") te ti) 0.001)
      (strcat "wall role thickness " (ct:get "id" wall))))
  (foreach room (ct:get "rooms" model)
    (setq b (ct:get "bounds" room))
    (ct:assert (equal (ct:get "net_area_m2" room)
      (/ (* (- (nth 2 b) (nth 0 b)) (- (nth 3 b) (nth 1 b))) 1000000.0) 0.000001) "net area matches clear bounds")
    (if (/= (ct:get "kind" room) "corridor")
      (progn
        (if (not (equal last-bottom (nth 1 b) 0.001))
          (progn
            (if last-top
              (ct:assert (equal (- (nth 1 b) last-top) ti 0.001) "row gap is internal wall thickness")
              (ct:assert (equal (- (nth 1 b) (nth 1 house)) te 0.001) "first row starts at exterior inner face"))
            (setq rows (1+ rows) sum-depth (+ sum-depth (- (nth 3 b) (nth 1 b)))
              last-bottom (nth 1 b) last-top (nth 3 b)))))))
  (ct:assert (equal (- (nth 3 house) last-top) te 0.001) "last row ends at exterior inner face")
  (ct:assert (equal (- (nth 3 house) (nth 1 house)) (+ (* 2 te) sum-depth (* (1- rows) ti)) 0.001)
    "overall depth equals clear rows plus physical walls"))

(defun ct:run (path / ct:file ct:passed ct:failed params result repeat-result seed p-float key pa pb ma mb ra rb)
  (setq ct:file (open path "w") ct:passed 0 ct:failed 0)
  (setq params (ct:params 42))
  (setq result (cg:generate params))
  (ct:assert result "generator returns a model")
  (setq repeat-result (cg:generate params))
  (ct:assert (equal result repeat-result 0.000001) "same seed produces same model")
  (ct:assert (cdr (assoc "rooms" result)) "model contains rooms")
  (ct:assert (cdr (assoc "walls" result)) "model contains walls")
  (ct:assert (cdr (assoc "openings" result)) "model contains openings")
  (ct:assert (cdr (assoc "furniture" result)) "model contains furniture")
  (ct:geometry result "baseline")
  (ct:program result params)
  (setq seed 1)
  (repeat 25
    (setq result (cg:generate (ct:params seed)))
    (ct:assert (not (ct:get "error" result)) (strcat "seed " (itoa seed) " succeeds"))
    (if (not (ct:get "error" result)) (ct:geometry result (strcat "seed " (itoa seed))))
    (setq seed (1+ seed)))
  (setq repeat-result (subst (cons "dining" 1) (assoc "dining" params) params))
  (setq result (cg:generate repeat-result))
  (ct:assert (not (ct:get "error" result)) "odd room count succeeds")
  (if (not (ct:get "error" result))
    (progn (ct:geometry result "odd program") (ct:program result repeat-result)))
  (setq result (cg:generate (subst (cons "furniture" 0) (assoc "furniture" params) params)))
  (ct:assert (and (ct:get "rooms" result) (null (ct:get "furniture" result))) "furniture toggle preserves rooms and omits furniture")
  (setq result (cg:generate (subst (cons "lot_depth" 6000.0) (assoc "lot_depth" params) params)))
  (ct:assert (ct:get "error" result) "infeasible lot is rejected")
  (setq result (cg:generate (subst (cons "bedrooms" 1.5) (assoc "bedrooms" params) params)))
  (ct:assert (ct:get "error" result) "fractional room count is rejected")
  (setq result (cg:generate (subst (cons "wall" -150.0) (assoc "wall" params) params)))
  (ct:assert (ct:get "error" result) "negative wall thickness is rejected")
  (setq p-float params)
  (foreach key '("bedrooms" "bathrooms" "living" "kitchens" "laundry" "dining" "office" "seed")
    (setq p-float (subst (cons key (float (ct:get key p-float))) (assoc key p-float) p-float)))
  (setq result (cg:generate p-float))
  (ct:assert (not (ct:get "error" result)) "integer-valued floats from DCL accepted")
  (ct:program result p-float)
  (ct:geometry result "DCL float values")
  (setq pa (append '(("wall_internal" . 100.0) ("wall_external" . 250.0)) p-float)
        pb (append '(("wall_internal" . 250.0) ("wall_external" . 100.0)) p-float)
        ma (cg:generate pa) mb (cg:generate pb))
  (ct:geometry ma "internal100 external250")
  (ct:geometry mb "internal250 external100")
  (ct:wall-profile ma 100.0 250.0)
  (ct:wall-profile mb 250.0 100.0)
  (ct:assert (equal ma (cg:generate (vl-remove (assoc "wall" pa) pa)) 0.000001)
    "explicit thicknesses work without legacy wall field")
  (foreach ra (ct:get "rooms" ma)
    (if (/= (ct:get "kind" ra) "corridor")
      (foreach rb (ct:get "rooms" mb)
        (if (= (ct:get "id" ra) (ct:get "id" rb))
          (progn
            (ct:assert (equal (- (nth 3 (ct:get "bounds" ra)) (nth 1 (ct:get "bounds" ra)))
              (- (nth 3 (ct:get "bounds" rb)) (nth 1 (ct:get "bounds" rb))) 0.001)
              "swapping wall thickness preserves requested clear row depth")
            (ct:assert (equal (ct:get "net_area_m2" ra) (ct:get "net_area_m2" rb) 0.000001)
              "swapping equal-sum thickness preserves paired room clear area"))))))
  (setq pa (subst (cons "dining" 1.0) (assoc "dining" pa) pa))
  (setq result (cg:generate pa))
  (ct:geometry result "odd asymmetric thickness")
  (ct:wall-profile result 100.0 250.0)
  (write-line (strcat "COMPLETE passed=" (itoa ct:passed) " failed=" (itoa ct:failed)) ct:file)
  (close ct:file)
  (princ))
(princ)
