;;; Union boundary of orthogonal wall solids, with openings retained.
(defun cj:inside (p boxes / found b)
 (setq found nil)
 (foreach b boxes (if (and (> (car p) (car b)) (< (car p) (nth 2 b))
  (> (cadr p) (cadr b)) (< (cadr p) (nth 3 b))) (setq found T))) found)
(defun cj:extension (p walls / other a b result)
 (setq result 0.0)
 (foreach other walls
  (setq a (cg:get "start" other) b (cg:get "end" other))
  (if (and (equal (car a) (car b) 0.01) (equal (car p) (car a) 0.01)
    (<= (- (min (cadr a) (cadr b)) 0.01) (cadr p))
    (>= (+ (max (cadr a) (cadr b)) 0.01) (cadr p)))
   (setq result (max result (/ (cg:get "thickness" other) 2.0))))) result)
(defun cj:boxes (walls openings / result w a b h horizontal low high gaps o c gap pos ext0 ext1)
 (setq result nil)
 (foreach w walls
  (setq a (cg:get "start" w) b (cg:get "end" w) h (/ (cg:get "thickness" w) 2.0)
   horizontal (equal (cadr a) (cadr b) 0.01) gaps nil)
  (if horizontal
   (setq low (min (car a) (car b)) high (max (car a) (car b))
    ext0 (cj:extension (list low (cadr a)) walls) ext1 (cj:extension (list high (cadr a)) walls))
   (setq low (min (cadr a) (cadr b)) high (max (cadr a) (cadr b)) ext0 0.0 ext1 0.0))
  (foreach o openings (if (= (cg:get "wall_id" o) (cg:get "id" w))
   (progn (setq c (if horizontal (car (cg:get "center" o)) (cadr (cg:get "center" o))))
    (setq gaps (cons (list (- c (/ (cg:get "width" o) 2.0)) (+ c (/ (cg:get "width" o) 2.0))) gaps)))))
  (setq pos (- low ext0) gaps (append (vl-sort gaps '(lambda (u v) (< (car u) (car v)))) (list (list (+ high ext1) (+ high ext1)))))
  (foreach gap gaps
   (if (> (- (car gap) pos) 0.01)
    (setq result (cons (if horizontal (list pos (- (cadr a) h) (car gap) (+ (cadr a) h))
     (list (- (car a) h) pos (+ (car a) h) (car gap))) result)))
   (setq pos (max pos (cadr gap))))) result)
(defun cj:edge (horizontal fixed low high boxes / cuts b value vals p q mid one two result)
 (setq cuts (list low high) result nil)
 (foreach b boxes
  (foreach value (if horizontal (list (car b) (nth 2 b)) (list (cadr b) (nth 3 b)))
   (if (and (> value low) (< value high)) (setq cuts (cons value cuts)))))
 (setq vals (vl-sort cuts '<))
 (while (cdr vals)
  (setq p (car vals) q (cadr vals) mid (/ (+ p q) 2.0)
   one (if horizontal (list mid (- fixed 0.005)) (list (- fixed 0.005) mid))
   two (if horizontal (list mid (+ fixed 0.005)) (list (+ fixed 0.005) mid)))
  (if (and (> (- q p) 0.01) (not (eq (cj:inside one boxes) (cj:inside two boxes))))
   (setq result (cons (if horizontal (list (list p fixed) (list q fixed)) (list (list fixed p) (list fixed q))) result)))
  (setq vals (cdr vals))) result)
(defun cj:segments (boxes / result b edge segment)
 (setq result nil)
 (foreach b boxes
  (foreach edge (list (list T (cadr b) (car b) (nth 2 b)) (list T (nth 3 b) (car b) (nth 2 b))
    (list nil (car b) (cadr b) (nth 3 b)) (list nil (nth 2 b) (cadr b) (nth 3 b)))
   (foreach segment (cj:edge (car edge) (cadr edge) (nth 2 edge) (nth 3 edge) boxes)
    (if (not (member segment result)) (setq result (cons segment result)))))) result)
(defun cj:draw (model / segment)
 (foreach segment (cj:segments (cj:boxes (cg:get "walls" model) (cg:get "openings" model)))
  (cg:line (car segment) (cadr segment) "CASA_PAREDES" "WALL-UNION")))

;;; Choose dimension lines in the least occupied strip of each room.
(defun cj:position (b horizontal model / ratio pos low high strip score best bestscore obj box area)
 (setq bestscore 1e99 best nil)
 (foreach ratio '(0.12 0.88 0.25 0.75 0.4 0.6 0.5)
  (setq low (if horizontal (cadr b) (car b)) high (if horizontal (nth 3 b) (nth 2 b))
   pos (+ low (* ratio (- high low)))
   strip (if horizontal (list (car b) (- pos 60) (nth 2 b) (+ pos 230))
    (list (- pos 230) (cadr b) (+ pos 60) (nth 3 b))) score 0.0)
  (foreach box (append (mapcar '(lambda (f) (cg:get "bounds" f)) (cg:get "furniture" model)) *cj-label-boxes* (cf:doors b model))
   (setq area (* (max 0 (- (min (nth 2 strip) (nth 2 box)) (max (car strip) (car box))))
     (max 0 (- (min (nth 3 strip) (nth 3 box)) (max (cadr strip) (cadr box))))))
   (setq score (+ score area)))
  (if (< score bestscore) (setq bestscore score best pos))) best)
;;; Clear room dimensions stay with their room, overall dimensions outside lot.
(defun cj:dimensions (model / room b site house x0 y0 x1 y1 id dx dy pts a z)
 (setq site (cg:get "site_bounds" model) house (cg:get "house_bounds" model)
  x0 (car house) y0 (cadr house) x1 (nth 2 house) y1 (nth 3 house))
 (foreach room (cg:get "rooms" model)
  (setq b (cg:get "bounds" room) id (cg:get "id" room)
   dy (cj:position b T model) dx (cj:position b nil model))
  (cg:dim (list (car b) dy) (list (nth 2 b) dy)
   (list (car b) dy) (strcat "DX-CLEAR-" id))
  (if (/= (cg:get "kind" room) "corridor")
   (cg:dim (list dx (cadr b)) (list dx (nth 3 b))
    (list dx (cadr b)) (strcat "DY-CLEAR-" id))))
 ;; Locate the inset edges from the actual footprint, not its bounding box.
 (setq pts (append (cg:get "footprint" model) (list (car (cg:get "footprint" model)))))
 (while (cdr pts)
  (setq a (car pts) z (cadr pts))
  (cond
   ((and (equal (cadr a) (cadr z) 0.01) (> (cadr a) (+ y0 1)) (< (cadr a) (- y1 1)))
    (cg:dim a z (list (car a) (+ (cadr a) (if (> (cadr a) (/ (+ y0 y1) 2)) 600 -600))) "DIM-RECESS-W"))
   ((and (equal (car a) (car z) 0.01) (> (car a) (+ x0 1)) (< (car a) (- x1 1)))
    (cg:dim a z (list (if (> (car a) (/ (+ x0 x1) 2)) (+ x1 600) (- x0 600)) (cadr a)) "DIM-RECESS-D")))
  (setq pts (cdr pts)))
 (cg:dim (list x0 y0) (list x1 y0) (list x0 (- (cadr site) 700)) "DIM-HOUSE-W")
 (cg:dim (list x0 y0) (list x0 y1) (list (- (car site) 700) y0) "DIM-HOUSE-D")
 (cg:dim (list (car site) (cadr site)) (list (nth 2 site) (cadr site))
  (list (car site) (- (cadr site) 1400)) "DIM-SITE-W")
 (cg:dim (list (nth 2 site) (cadr site)) (list (nth 2 site) (nth 3 site))
  (list (+ (nth 2 site) 1500) (cadr site)) "DIM-SITE-D"))
